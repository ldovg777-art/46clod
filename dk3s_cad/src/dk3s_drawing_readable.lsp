;;; ============================================================================
;;;  dk3s_drawing.lsp  —  Чертёж общего вида датчика концентрации ДК-3С-210АВ
;;;  Версия: 1.3.5  (2026-09-28)
;;;  Платформа: nanoCAD / AutoCAD / BricsCAD / ZWCAD (AutoLISP, только entmake)
;;;
;;;  Источник геометрии:
;;;    - «Техническое описание K1» (англ.), стр. 16 — монтажный чертёж датчика
;;;      (векторная графика, масштаб восстановлен по размеру 411 мм);
;;;    - Fig. 1 (общий вид), Fig. 4 (узел рабочего электрода: Ø1,4 мм, выступ 2 мм).
;;;
;;;  Команда:  DK3S   — строит чертёж (формат А2, масштаб 1:2) в текущем документе: главный вид,
;;;            выносной элемент А (2:1), изометрия с вырезом (1:2, раздел 11), технические требования.
;;;            Всё в пространстве модели: датчик 1:1, рамка и надписи увеличены в 2 раза,
;;;            печать листа с масштабом 1:2 даёт А2.
;;;
;;;  Кириллица в строках записана как \U+XXXX — работает при любой кодировке файла.
;;;  Все размеры вынесены в таблицу параметров (раздел 1) — правьте только её.
;;; ============================================================================

;;; ---------------------------------------------------------------------------
;;; 1. ТАБЛИЦА ПАРАМЕТРОВ (мм). Ось Z — вдоль датчика от вершины скобы,
;;;    R — радиус/смещение от оси. В главном виде Z направлена вправо, R — вверх.
;;; ---------------------------------------------------------------------------

;; --- Лист и оформление --------------------------------------------------------
(setq g_dk3s_sheet_w      594.0)   ; формат А2 (альбомный), мм бумаги — с изометрией на А3 не помещается
(setq g_dk3s_sheet_h      420.0)
(setq g_dk3s_format       "А2")    ; надпись «Формат» под основной надписью
;; компоновка листа, мм бумаги от левого нижнего угла: вверху главный вид и справа от него элемент А,
;; внизу изометрия, справа над основной надписью — технические требования
(setq g_dk3s_main_x       48.0)    ; главный вид: вершина скобы на оси
(setq g_dk3s_main_y       338.0)
(setq g_dk3s_det_x        430.0)   ; выносной элемент А: начало его координат (обрыв трубки)
(setq g_dk3s_det_y        360.0)
(setq g_dk3s_notes_x      404.0)   ; технические требования: левый край (по основной надписи), верх не выше
(setq g_dk3s_notes_y      178.0)
(setq g_dk3s_iso_x        72.0)    ; изометрия: левый нижний угол картинки
(setq g_dk3s_iso_y        60.0)
(setq g_dk3s_scale_den    2.0)     ; знаменатель масштаба главного вида (1:2)
(setq g_dk3s_detail_mul   4.0)     ; выносной элемент А: 4x в модели = 2:1 на листе
(setq g_dk3s_font         "GOST.shx")       ; шрифт надписей как в чертежах ЭКОР (стиль GOST, наклон 15); в поставке nanoCAD его нет:
                                           ; скопировать GOST.shx в C:\ProgramData\Nanosoft\nanoCAD XX\SHX или поставить "CS_Gost2304.shx"
(setq g_dk3s_txt_h        3.5)     ; высота текста на бумаге, мм
(setq g_dk3s_font_k       1.08)    ; запас по ширине надписей сверх пропорций ГОСТ 2.304 тип Б (другой шрифт, подмена)
;; толщины линий (сотые мм) как в чертежах ЭКОР: контур 0,6; тонкие 0,3; рамка 0,6; размеры и текст 0,25
(setq g_dk3s_lw_main 60)  (setq g_dk3s_lw_thin 30)  (setq g_dk3s_lw_frame 60)  (setq g_dk3s_lw_dim 25)
(setq g_dk3s_lw_iso 50)    ; контур изометрии: чуть тоньше основного — линии в вырезе стоят тесно
(setq g_dk3s_designation  "302123.000 ВО")   ; обозначение общего вида: 302123.000 — датчик (перв. примен. корпуса, гайки, грундбуксы); подтверждено 19.09.2026
(setq g_dk3s_name1        "Датчик концентрации")
(setq g_dk3s_name2        "ДК-3С-210АВ")
(setq g_dk3s_name3        "Общий вид")
(setq g_dk3s_org1         "ООО НТП \"Экор\"")   ; графа организации 50x15, две строки
(setq g_dk3s_org2         "Львов")
(setq g_dk3s_author       "")      ; Разраб. (фамилия)
(setq g_dk3s_checker      "")      ; Пров.

;; --- Защитная скоба и наконечник ---------------------------------------------
(setq g_dk3s_guard_h      15.6)    ; высота скобы над торцом гильзы
(setq g_dk3s_guard_w      28.0)    ; ширина скобы (наружная)
(setq g_dk3s_guard_d      2.0)     ; диаметр проволоки скобы
(setq g_dk3s_guard_r      4.0)     ; наружный радиус гиба скобы
(setq g_dk3s_tip_off      5.5)     ; смещение оси наконечника от оси датчика
(setq g_dk3s_tip_d        7.0)     ; наконечник (фторопласт): тело Ø7, шестигранник 1/4" фрезерован по Ø7
(setq g_dk3s_tip_s        6.35)    ; размер под ключ наконечника
(setq g_dk3s_tip_len      18.3)    ; тело Ø7: цилиндр 12,5 + шестигранник 5,8 (Fig. 4/5 техописания K1)
(setq g_dk3s_tip_cone     3.5)     ; длина конуса наконечника (Fig. 4)
(setq g_dk3s_tip_nose_d   1.8)     ; диаметр торца носика
(setq g_dk3s_tip_vis      3.7)     ; выступ шестигранника над торцом гильзы
(setq g_dk3s_we_d         1.4)     ; рабочий электрод: проволока Ø1,4
(setq g_dk3s_we_len       2.0)     ; выступ рабочего электрода из наконечника
(setq g_dk3s_tube_d       6.0)     ; защитная трубка токоотвода (наружный Ø)
(setq g_dk3s_tube_wall    0.5)     ; стенка защитной трубки
(setq g_dk3s_tap_d        3.0)     ; токоотвод рабочего электрода (резьба M3x0,5 — на неё накручен наконечник)
(setq g_dk3s_tap_minor_d  2.46)    ; внутренний диаметр резьбы M3x0,5 (тонкая линия)
(setq g_dk3s_tap_cone_z1  13.6)    ; конус на конце токоотвода: начало и конец от торца тела наконечника
(setq g_dk3s_tap_cone_z2  18.7)    ; (Fig. 4: токоотвод конусом переходит в электрод Ø1,4)
(setq g_dk3s_tip_shank_d  5.0)     ; хвостовик наконечника под трубку: по её внутреннему Ø, натяг
(setq g_dk3s_tip_shank_l  15.0)    ; длина хвостовика (трубка надета на всю длину)
(setq g_dk3s_tip_bore_end 20.0)    ; дно отверстия Ø3 от торца тела, дальше канал электрода в носике

;; --- Защитная гильза ----------------------------------------------------------
(setq g_dk3s_z_sleeve     15.6)    ; торец гильзы
(setq g_dk3s_sleeve_d     32.0)    ; наружный диаметр гильзы
(setq g_dk3s_hole_d       6.0)     ; перфорация: диаметр отверстий
(setq g_dk3s_hole_z1      25.5)    ; первое фронтальное отверстие (от вершины скобы)
(setq g_dk3s_hole_pitch   20.0)    ; шаг отверстий в ряду
(setq g_dk3s_hole_n       3)       ; отверстий во фронтальном ряду
(setq g_dk3s_hole_side_n  2)       ; боковых отверстий на сторону (в шахматном порядке)

;; --- Корпус 714.761.000 (S46, M42x3, фланец Ø59, длина 61), гайка нажимная 714.541.000 (S36, M33x2) ---
(setq g_dk3s_z_shell      224.8)   ; торец резьбы M42x3 корпуса (правый торец корпуса 285.8, длина 61 h12)
(setq g_dk3s_shell_d      42.0)    ; наружный диаметр резьбы M42x3-6f
(setq g_dk3s_thread_pitch 3.0)
(setq g_dk3s_shell_ch     1.0)     ; фаска торца корпуса 1x45
(setq g_dk3s_z_relief     253.8)   ; начало проточки перед фланцем (34 от торца до фланца)
(setq g_dk3s_relief_d     39.0)
(setq g_dk3s_z_plate      258.8)   ; фланец-пластина
(setq g_dk3s_plate_d      59.0)
(setq g_dk3s_z_hex1       265.8)   ; шестигранник S46 корпуса
(setq g_dk3s_hex1_s       46.0)
(setq g_dk3s_hex1_e       52.0)    ; по углам S46 (Ø52 по чертежу корпуса 714.761.000); фаска 30° со стороны гайки
(setq g_dk3s_z_cyl        285.8)   ; правый торец корпуса; далее видимая резьба M33x2 гайки нажимной
(setq g_dk3s_cyl_d        33.0)    ; M33x2-6g гайки
(setq g_dk3s_thread2_pitch 2.0)
(setq g_dk3s_z_groove     293.2)   ; канавка Ø30 x 3 у шестигранника гайки
(setq g_dk3s_groove_d     30.0)
(setq g_dk3s_z_hex2       296.6)   ; шестигранник S36 гайки нажимной (длина 10, фаска 30° с наружного торца)
(setq g_dk3s_hex2_s       36.0)
(setq g_dk3s_hex2_e       41.0)    ; по углам S36 (Ø41 по чертежу гайки 714.541.000)
(setq g_dk3s_z_neck       306.6)   ; труба электродного узла Ø20,8 (проходит через гайку и грундбуксу)
(setq g_dk3s_neck_d       20.8)
(setq g_dk3s_z_step       314.6)   ; ступень Ø18,8
(setq g_dk3s_step_d       18.8)
(setq g_dk3s_z_taper      315.6)   ; конус Ø16 -> Ø15,4
(setq g_dk3s_taper_d1     16.0)
(setq g_dk3s_taper_d2     15.4)
(setq g_dk3s_z_tag        325.2)   ; бирка с заводским номером
(setq g_dk3s_tag_w        16.0)
(setq g_dk3s_z_tag_end    335.1)

;; --- Токоотводы, мостики, хомуты ----------------------------------------------
(setq g_dk3s_bridge_d     6.0)     ; электролитический мостик — трубка Ø6, как трубка РЭ (K1, лист 16: развилка у ЭС)
(setq g_dk3s_bridge_r     3.0)     ; ось мостика на виде: жгут — три трубки треугольником, мостики за трубкой РЭ,
                                   ; из-за неё видна полоса 3 мм (контур жгута ±6)
(setq g_dk3s_z_clamp1     367.0)   ; хомуты (начало), длина и диаметр
(setq g_dk3s_z_clamp2     467.2)
(setq g_dk3s_clamp_len    7.6)
(setq g_dk3s_clamp_d      13.6)
(setq g_dk3s_z_bend       476.0)   ; начало разводки мостиков к электродам сравнения
(setq g_dk3s_z_we_end     483.7)   ; конец трубки Ø6, начало разъёма WE
(setq g_dk3s_conn_collar_d 8.0)    ; разъём (штырь): буртик, корпус, штырь
(setq g_dk3s_conn_collar_l 2.0)
(setq g_dk3s_conn_body_d  6.5)
(setq g_dk3s_conn_body_l  14.0)
(setq g_dk3s_conn_pin_d   2.5)
(setq g_dk3s_conn_pin_l   14.0)
(setq g_dk3s_conn_tip_l   1.0)
(setq g_dk3s_se_r         -24.6)   ; ось провода вспомогательного электрода (снизу)
(setq g_dk3s_se_d         3.0)
(setq g_dk3s_z_se_start   283.7)
(setq g_dk3s_z_se_end     481.9)

;; --- Электроды сравнения (2 шт.) ----------------------------------------------
(setq g_dk3s_re_r         22.8)    ; ось электрода сравнения от оси датчика
(setq g_dk3s_re_d         20.0)
(setq g_dk3s_z_re         521.7)   ; верх (начало) электрода сравнения
(setq g_dk3s_re_seg1      24.1)    ; первый сегмент
(setq g_dk3s_re_neck      3.0)     ; перемычка Ø16
(setq g_dk3s_re_neck_d    16.0)
(setq g_dk3s_re_seg2      34.0)    ; второй сегмент
(setq g_dk3s_re_gap       1.0)     ; зазор до буртика штыря

;; --- Станции вертикальных размеров главного вида (от вершины скобы) -------------
(setq g_dk3s_zdim_sleeve  130.0)   ; Ø32 гильзы (число на оси — осевая под ним прерывается)
(setq g_dk3s_zdim_thread  246.0)   ; M42x3 корпуса (то же)
(setq g_dk3s_zdim_wire    350.0)   ; Ø3 провода ВЭ (число под проводом, левее надписи о нём)
(setq g_dk3s_zdim_tube    455.0)   ; Ø6 трубки токоотвода (число над верхним мостиком)
(setq g_dk3s_zdim_re      565.0)   ; Ø20 электрода сравнения (число над верхним электродом)

;; --- Итоговые (вычисляются) ---------------------------------------------------
(setq g_dk3s_z_re_end     (+ g_dk3s_z_re g_dk3s_re_seg1 g_dk3s_re_neck g_dk3s_re_seg2))   ; 582.8
(setq g_dk3s_z_total      (+ g_dk3s_z_re_end g_dk3s_re_gap g_dk3s_conn_body_l 1.0
                             g_dk3s_conn_pin_l g_dk3s_conn_tip_l))                         ; 613.8

;;; ---------------------------------------------------------------------------
;;; 2. СЛУЖЕБНЫЕ ПЕРЕМЕННЫЕ (не править)
;;; ---------------------------------------------------------------------------
(setq g_dk3s_lay_main   "DK3S_CONTOUR")   ; основные линии 0,5
(setq g_dk3s_lay_thin   "DK3S_THIN")      ; тонкие линии 0,25 (штриховка, выноски)
(setq g_dk3s_lay_axis   "DK3S_AXIS")      ; осевые
(setq g_dk3s_lay_dim    "DK3S_DIM")       ; размеры
(setq g_dk3s_lay_text   "DK3S_TEXT")      ; надписи
(setq g_dk3s_lay_frame  "DK3S_FRAME")     ; рамка и основная надпись
(setq g_dk3s_lay_iso    "DK3S_ISO")       ; контур изометрии
(setq g_dk3s_style      "DK3S_GOST")      ; текстовый стиль
(setq g_dk3s_dimstyle   "DK3S")           ; размерный стиль
(setq g_dk3s_ltype_axis "DK3S_CENTER")    ; тип линии осевых
(setq g_dk3s_ox 0.0)  (setq g_dk3s_oy 0.0)  (setq g_dk3s_k 1.0)   ; текущее начало/масштаб вида
(setq g_dk3s_dim_mode "entmake")          ; "entmake" | "command" (авто-переключение при сбое)
(setq g_dk3s_stage "")                    ; текущая стадия построения (FSM, для диагностики)
(setq g_dk3s_cnt 0)                       ; счётчик созданных примитивов

;;; ---------------------------------------------------------------------------
;;; 3. ПРИМИТИВЫ (entmake). Все координаты — модель, мм.
;;; ---------------------------------------------------------------------------

;; Точка вида: z вдоль оси, r поперёк; учитывает начало и масштаб текущего вида
(defun dk3s_p (z r)
  (list (+ g_dk3s_ox (* g_dk3s_k z)) (+ g_dk3s_oy (* g_dk3s_k r)) 0.0)
)

;; Изометрия (раздел 11): точка — мм бумаги от левого нижнего угла картинки -> модель листа
(defun dk3s_iso_p (x y / s)
  (setq s g_dk3s_scale_den)
  (list (* s (+ g_dk3s_iso_x x)) (* s (+ g_dk3s_iso_y y)) 0.0)
)

;; Полилиния изометрии из плоского списка (x1 y1 x2 y2 ...) в мм бумаги
(defun dk3s_iso_pl (xy / pts)
  (while xy
    (setq pts (cons (dk3s_iso_p (car xy) (cadr xy)) pts) xy (cddr xy))
  )
  (dk3s_pline (reverse pts) nil 0.0 g_dk3s_lay_iso)
)

;; Отрезок изометрии (штриховка, ось) в мм бумаги
(defun dk3s_iso_ln (x1 y1 x2 y2 lay)
  (dk3s_line (dk3s_iso_p x1 y1) (dk3s_iso_p x2 y2) lay)
)

;; Точка листа (абсолютная)
(defun dk3s_ps (x y) (list x y 0.0))

;; Масштабированная длина (для радиусов, высот текста в текущем виде)
(defun dk3s_l (v) (* g_dk3s_k v))

(defun dk3s_deg (a) (* 180.0 (/ a pi)))
(defun dk3s_rad (a) (* pi (/ a 180.0)))


;; Число строкой с запятой в качестве разделителя (ЕСКД), prec — знаков после запятой
(defun dk3s_num (v prec / s i c r)
  (setq s (rtos v 2 prec) r "" i 1)
  (while (<= i (strlen s))
    (setq c (substr s i 1))
    (setq r (strcat r (if (= c ".") "," c)))
    (setq i (1+ i))
  )
  r
)


;; Число видимых знаков в строке: код \U+XXXX (7 символов) считается одним знаком
(defun dk3s_strlen_vis (s / i n)
  (setq i 1 n 0)
  (while (<= i (strlen s))
    (if (= (substr s i 3) "\\U+") (setq i (+ i 7)) (setq i (1+ i)))
    (setq n (1+ n))
  )
  n
)

;; Учёт созданного примитива
(defun dk3s_made (r) (if r (setq g_dk3s_cnt (1+ g_dk3s_cnt))) r)

(defun dk3s_line (p1 p2 lay)
  (dk3s_made (entmake (list '(0 . "LINE") '(100 . "AcDbEntity") (cons 8 lay)
                            '(100 . "AcDbLine") (cons 10 p1) (cons 11 p2))))
)

(defun dk3s_circle (c r lay)
  (dk3s_made (entmake (list '(0 . "CIRCLE") '(100 . "AcDbEntity") (cons 8 lay)
                            '(100 . "AcDbCircle") (cons 10 c) (cons 40 r))))
)

;; Дуга: углы в градусах, против часовой стрелки от a1 к a2
(defun dk3s_arc (c r a1 a2 lay)
  (dk3s_made (entmake (list '(0 . "ARC") '(100 . "AcDbEntity") (cons 8 lay)
                            '(100 . "AcDbCircle") (cons 10 c) (cons 40 r)
                            '(100 . "AcDbArc") (cons 50 a1) (cons 51 a2))))
)

;; Дуга через три точки p1 -> p2 -> p3 (p2 — любая промежуточная точка дуги); точки — модель
(defun dk3s_arc3 (p1 p2 p3 lay / ax ay bx by cx cy d ux uy c a1 a2 a3 tw)
  (setq ax (car p1) ay (cadr p1) bx (car p2) by (cadr p2) cx (car p3) cy (cadr p3))
  (setq d (* 2.0 (+ (* ax (- by cy)) (* bx (- cy ay)) (* cx (- ay by)))))
  (setq ux (/ (+ (* (+ (* ax ax) (* ay ay)) (- by cy)) (* (+ (* bx bx) (* by by)) (- cy ay))
                 (* (+ (* cx cx) (* cy cy)) (- ay by))) d)
        uy (/ (+ (* (+ (* ax ax) (* ay ay)) (- cx bx)) (* (+ (* bx bx) (* by by)) (- ax cx))
                 (* (+ (* cx cx) (* cy cy)) (- bx ax))) d))
  (setq c (list ux uy 0.0) tw (* 2.0 pi))
  (setq a1 (angle c p1) a2 (angle c p2) a3 (angle c p3))
  ;; против часовой от a1 к a3 должна лежать a2, иначе дуга идёт от a3 к a1
  (if (< (rem (+ (- a2 a1) tw tw) tw) (rem (+ (- a3 a1) tw tw) tw))
    (dk3s_arc c (distance c p1) (dk3s_deg a1) (dk3s_deg a3) lay)
    (dk3s_arc c (distance c p1) (dk3s_deg a3) (dk3s_deg a1) lay))
)

;; Полилиния по списку 3D-точек; closed = T/nil; width — постоянная ширина
(defun dk3s_pline (pts closed width lay / lst)
  (setq lst (list '(0 . "LWPOLYLINE") '(100 . "AcDbEntity") (cons 8 lay)
                  '(100 . "AcDbPolyline") (cons 90 (length pts))
                  (cons 70 (if closed 1 0)) (cons 43 width)))
  (foreach p pts (setq lst (append lst (list (list 10 (car p) (cadr p))))))
  (dk3s_made (entmake lst))
)

;; Прямоугольник по двум противоположным углам (замкнутая полилиния)
(defun dk3s_rect (p1 p2 lay)
  (dk3s_pline (list p1 (list (car p2) (cadr p1) 0.0) p2 (list (car p1) (cadr p2) 0.0)) T 0.0 lay)
)

;; Закрашенная точка (полилиния из двух дуг с шириной = диаметру)
(defun dk3s_dot (c d lay / lst)
  (setq lst (list '(0 . "LWPOLYLINE") '(100 . "AcDbEntity") (cons 8 lay)
                  '(100 . "AcDbPolyline") '(90 . 2) '(70 . 1) (cons 43 d)
                  (list 10 (- (car c) (/ d 4.0)) (cadr c)) '(42 . 1.0)
                  (list 10 (+ (car c) (/ d 4.0)) (cadr c)) '(42 . 1.0)))
  (dk3s_made (entmake lst))
)

;; Эллипс через полилинию (портативно: без entmake ELLIPSE)
;; c — центр, a — полуось по X, b — полуось по Y
(defun dk3s_ellipse (c a b lay / i n pts ang)
  (setq n 32 i 0 pts nil)
  (while (< i n)
    (setq ang (* 2.0 pi (/ i (float n))))
    (setq pts (cons (list (+ (car c) (* a (cos ang))) (+ (cadr c) (* b (sin ang))) 0.0) pts))
    (setq i (1+ i))
  )
  (dk3s_pline (reverse pts) T 0.0 lay)
)

;; Текст: p — точка вставки, h — высота, rot — градусы,
;; just — 0 левый/низ, 1 центр/центр, 2 правый/низ, 3 центр/низ, 4 левый/середина
(defun dk3s_text (p h str rot just lay)
  (dk3s_text_wf p h str rot just lay 1.0)
)

;; То же с коэффициентом ширины wf (группа 41): так в штампах ЭКОР подгоняют надпись под графу
(defun dk3s_text_wf (p h str rot just lay wf / hj vj)
  (cond ((= just 1) (setq hj 1 vj 2))
        ((= just 2) (setq hj 2 vj 0))
        ((= just 3) (setq hj 1 vj 0))
        ((= just 4) (setq hj 0 vj 2))
        (T (setq hj 0 vj 0)))
  (dk3s_made (entmake (list '(0 . "TEXT") '(100 . "AcDbEntity") (cons 8 lay)
                            '(100 . "AcDbText") (cons 10 p) (cons 40 h) (cons 1 str)
                            (cons 50 rot) (cons 41 wf) (cons 7 g_dk3s_style) (cons 72 hj) (cons 11 p)
                            '(100 . "AcDbText") (cons 73 vj))))
)

;; Оценка ширины надписи (в единицах h) при коэффициенте ширины 1 — с запасом, по пропорциям
;; шрифта ГОСТ 2.304 тип Б (таков CS_Gost2304.shx nanoCAD; GOST.shx ЭКОР тоже широкий — в их
;; штампах подписи сжаты до 0,6-0,95): прописная 0,8h, строчная и цифра 0,7h, пробел 0,6h,
;; точка, запятая, скобки, дефис 0,45h; плюс вынос наклона 15 градусов 0,27h.
;; Коды кириллицы (обратный слэш, U+, четыре цифры) считаются одним знаком.
(defun dk3s_text_w (s h / i n c k w)
  (setq i 1 w 0.0 n (strlen s))
  (while (<= i n)
    (setq c (ascii (substr s i 1)))
    (if (and (= c 92) (= (substr s (1+ i) 2) "U+"))
      (progn
        (setq k (dk3s_hex4 (substr s (+ i 3) 4)))
        (setq w (+ w (cond ((or (= k 1025) (and (>= k 1040) (<= k 1071))) 0.8)
                           ((= k 8470) 1.0)
                           (T 0.7))))
        (setq i (+ i 7)))
      (progn
        (setq w (+ w (cond ((and (>= c 65) (<= c 90)) 0.8)
                           ((= c 32) 0.6)
                           ((member c '(33 34 39 40 41 44 45 46 58 59 73 105 108)) 0.45)
                           (T 0.7))))
        (setq i (1+ i)))))
  (* h (+ w 0.27) g_dk3s_font_k)
)

;; Четыре шестнадцатеричные цифры -> целое (для кодов кириллицы)
(defun dk3s_hex4 (s / i c r)
  (setq i 1 r 0)
  (while (<= i (strlen s))
    (setq c (ascii (substr s i 1)))
    (setq r (+ (* r 16) (cond ((<= c 57) (- c 48)) ((<= c 70) (- c 55)) (T (- c 87)))))
    (setq i (1+ i)))
  r
)

;; Перенос по словам: первая строка не шире w1, следующие не шире w2 (единицы модели)
(defun dk3s_wrap (s h w1 w2 / words cur res i c lim)
  (setq words nil cur "" i 1)
  (while (<= i (strlen s))
    (setq c (substr s i 1))
    (if (= c " ")
      (progn (if (/= cur "") (setq words (cons cur words))) (setq cur ""))
      (setq cur (strcat cur c)))
    (setq i (1+ i)))
  (if (/= cur "") (setq words (cons cur words)))
  (setq words (reverse words) res nil cur "" lim w1)
  (foreach wd words
    (if (and (/= cur "") (> (dk3s_text_w (strcat cur " " wd) h) lim))
      (setq res (cons cur res) cur wd lim w2)
      (setq cur (if (= cur "") wd (strcat cur " " wd)))))
  (if (/= cur "") (setq res (cons cur res)))
  (reverse res)
)

;; Штриховка выпуклого многоугольника линиями под 45 градусов (sgn = 1) или 135 градусов (sgn = -1)
;; с шагом pitch (тонкие линии); точки — модель
(defun dk3s_hatch_dir (pts pitch lay sgn / cmin cmax c i n p1 p2 ts t1 t2 d x0 y0 x1 y1 den tt)
  ;; линии y = sgn*x + c ; c от min(y - sgn*x) до max(y - sgn*x) по вершинам
  (setq cmin nil cmax nil i 0 n (length pts))
  (while (< i n)
    (setq p1 (nth i pts) c (- (cadr p1) (* sgn (car p1))))
    (if (or (not cmin) (< c cmin)) (setq cmin c))
    (if (or (not cmax) (> c cmax)) (setq cmax c))
    (setq i (1+ i))
  )
  (setq d (* pitch (sqrt 2.0)))
  (setq c (+ cmin (/ d 2.0)))
  (while (< c cmax)
    ;; пересечения линии с рёбрами многоугольника; параметр t = x
    (setq ts nil i 0)
    (while (< i n)
      (setq p1 (nth i pts) p2 (nth (rem (1+ i) n) pts))
      (setq x0 (car p1) y0 (cadr p1) x1 (car p2) y1 (cadr p2))
      ;; ребро: (x,y) = p1 + s*(p2-p1), s in [0,1]; решаем y0 + s*dy = sgn*(x0 + s*dx) + c
      (setq den (- (- y1 y0) (* sgn (- x1 x0))))
      (if (> (abs den) 1e-9)
        (progn
          (setq tt (/ (- (+ (* sgn x0) c) y0) den))
          (if (and (>= tt -1e-9) (<= tt (+ 1.0 1e-9)))
            (setq ts (cons (+ x0 (* tt (- x1 x0))) ts))
          )
        )
      )
      (setq i (1+ i))
    )
    (if (>= (length ts) 2)
      (progn
        (setq t1 (apply 'min ts) t2 (apply 'max ts))
        (if (> (- t2 t1) 1e-6)
          (dk3s_line (list t1 (+ (* sgn t1) c) 0.0) (list t2 (+ (* sgn t2) c) 0.0) lay)
        )
      )
    )
    (setq c (+ c d))
  )
)

;; Штриховка металла (45 градусов) и «в клетку» — неметаллы, ГОСТ 2.306
(defun dk3s_hatch_poly (pts pitch lay) (dk3s_hatch_dir pts pitch lay 1.0))
(defun dk3s_hatch_cross (pts pitch lay)
  (dk3s_hatch_dir pts pitch lay 1.0)
  (dk3s_hatch_dir pts pitch lay -1.0)
)

;;; ---------------------------------------------------------------------------
;;; 4. ТАБЛИЦЫ: слои, тип линии, текстовый и размерный стили
;;; ---------------------------------------------------------------------------

(defun dk3s_make_ltype ()
  (if (not (tblsearch "LTYPE" g_dk3s_ltype_axis))
    (if (not (entmake (list '(0 . "LTYPE") '(100 . "AcDbSymbolTableRecord")
                            '(100 . "AcDbLinetypeTableRecord") (cons 2 g_dk3s_ltype_axis)
                            '(70 . 0) '(3 . "GOST 2.303-5 ____ _ ____ _ ____") '(72 . 65) '(73 . 4)
                            '(40 . 24.0) '(49 . 20.0) '(74 . 0) '(49 . -1.5) '(74 . 0)
                            '(49 . 1.0) '(74 . 0) '(49 . -1.5) '(74 . 0))))
      (setq g_dk3s_ltype_axis "Continuous")   ; запасной вариант — сплошная
    )
  )
)

;; Слой: color — номер цвета, lw — толщина в сотых мм (50 = 0,5 мм)
(defun dk3s_make_layer (name color ltype lw)
  (if (not (tblsearch "LAYER" name))
    (if (not (entmake (list '(0 . "LAYER") '(100 . "AcDbSymbolTableRecord")
                            '(100 . "AcDbLayerTableRecord") (cons 2 name) '(70 . 0)
                            (cons 62 color) (cons 6 ltype) (cons 370 lw))))
      ;; запасной вариант — через команду
      (command "_.-LAYER" "_M" name "_C" (itoa color) name "_L" ltype name "")
    )
  )
)

(defun dk3s_make_style ()
  (if (not (tblsearch "STYLE" g_dk3s_style))
    (if (not (entmake (list '(0 . "STYLE") '(100 . "AcDbSymbolTableRecord")
                            '(100 . "AcDbTextStyleTableRecord") (cons 2 g_dk3s_style)
                            '(70 . 0) '(40 . 0.0) '(41 . 1.0) '(50 . 15.0) '(71 . 0)
                            (cons 42 (* g_dk3s_txt_h g_dk3s_scale_den))
                            (cons 3 g_dk3s_font) '(4 . ""))))
      (setq g_dk3s_style "Standard")   ; запасной вариант — стандартный стиль
    )
  )
)

;; Размерный стиль как GOSTMTM/ЕСКД в чертежах ЭКОР: текст 3,5, стрелки 3,0, выносные 1,25,
;; отступ 0,625, зазор 0,625, DIMSCALE = знаменатель масштаба, запятая, нули подавляются, текст над линией
(defun dk3s_make_dimstyle ( / st lst)
  (if (not (tblsearch "DIMSTYLE" g_dk3s_dimstyle))
    (progn
      (setq lst (list '(0 . "DIMSTYLE") '(100 . "AcDbSymbolTableRecord")
                      '(100 . "AcDbDimStyleTableRecord") (cons 2 g_dk3s_dimstyle) '(70 . 0)
                      (cons 40 g_dk3s_scale_den)   ; DIMSCALE
                      '(41 . 3.0)                  ; DIMASZ
                      '(42 . 0.625)                ; DIMEXO
                      '(43 . 7.0)                  ; DIMDLI
                      '(44 . 1.25)                 ; DIMEXE
                      (cons 140 g_dk3s_txt_h)      ; DIMTXT
                      '(144 . 1.0)                 ; DIMLFAC
                      '(147 . 0.625)               ; DIMGAP
                      '(73 . 0) '(74 . 0)          ; DIMTIH DIMTOH — текст вдоль линии
                      '(77 . 1)                    ; DIMTAD — текст над линией
                      '(78 . 8)                    ; DIMZIN — без хвостовых нулей
                      '(271 . 1)                   ; DIMDEC — один знак
                      '(278 . 44)                  ; DIMDSEP — запятая
                      '(279 . 0)                   ; DIMTMOVE 0 — число прикреплено к размерной линии: CAD
                                                   ; продлевает линию до вынесенного числа и отодвигает его
                                                   ; за стрелки (при 1 — только если число далеко; опыт на ODA)
                      '(174 . 1)                   ; DIMTIX — число всегда между выносными (иначе nanoCAD
                                                   ; уводит невлезающее число на выноске — опыт на ODA)
                      '(172 . 1)                   ; DIMTOFL — линия между выносными всегда (ГОСТ 2.307,
                                                   ; и без неё nanoCAD не продлевает линию до вынесенного числа)
                      '(171 . 2) '(175 . 0) '(176 . 0) '(177 . 0)))
      (if (setq st (tblobjname "STYLE" g_dk3s_style))
        (setq lst (append lst (list (cons 340 st))))     ; DIMTXSTY
      )
      (if (not (entmake lst))
        (progn
          ;; запасной вариант: переменные текущего стиля + размеры командой
          (setq g_dk3s_dim_mode "command")
          (setvar "DIMSCALE" g_dk3s_scale_den) (setvar "DIMASZ" 3.0) (setvar "DIMEXO" 0.625)
          (setvar "DIMEXE" 1.25) (setvar "DIMTXT" g_dk3s_txt_h) (setvar "DIMGAP" 0.625)
          (setvar "DIMTIH" 0) (setvar "DIMTOH" 0) (setvar "DIMTAD" 1) (setvar "DIMZIN" 8) (setvar "DIMTIX" 1) (setvar "DIMTOFL" 1)
          (setvar "DIMTMOVE" 0)
          (setvar "DIMDEC" 1) (setvar "DIMDSEP" ",") (setvar "DIMTXSTY" g_dk3s_style)
        )
      )
    )
  )
)

;;; ---------------------------------------------------------------------------
;;; 5. РАЗМЕРЫ И ВЫНОСКИ
;;; ---------------------------------------------------------------------------

;; Линейный размер. p1, p2 — точки объекта; pd — точка на размерной линии;
;; rot — 0 (горизонтальный) или 90 (вертикальный); txt — "" (авто) или переопределение
;; ("%%c<>" — диаметр, "S<>" — под ключ и т.п.)
(defun dk3s_dim (p1 p2 pd rot txt)
  (dk3s_dim_t p1 p2 pd rot txt nil)
)

;; То же с заданным положением размерного числа tp (модель) или nil — число ставит CAD.
;; tp — когда число между выносными легло бы на линии детали: число выносится на продолжение
;; размерной линии за контур (ГОСТ 2.307, рис. 14). Группа 70 с флагом 128 + группа 11; при DIMTMOVE 0
;; поперёк линии tp задаёт саму размерную линию, вдоль — место числа; CAD продлевает линию до числа
;; и сам отодвигает его за стрелки (проверено на ODA — движке nanoCAD, 19.09.2026).
;; У вертикального размера p1 — нижняя точка: nanoCAD и AutoCAD ставят число слева от линии всегда,
;; а проверочный рендер (ezdxf) — по направлению p1 -> p2; так они совпадают.
(defun dk3s_dim_t (p1 p2 pd rot txt tp / r q)
  (if (and (= rot 90) (> (cadr p1) (cadr p2)))
    (setq q p1 p1 p2 p2 q)
  )
  (if (= g_dk3s_dim_mode "entmake")
    (progn
      (setq r (entmake (append
                         (list '(0 . "DIMENSION") '(100 . "AcDbEntity") (cons 8 g_dk3s_lay_dim)
                               '(100 . "AcDbDimension") (cons 10 pd))
                         (if tp (list (cons 11 tp)) nil)
                         (list (cons 70 (if tp 160 32)) (cons 1 txt) (cons 3 g_dk3s_dimstyle)
                               '(100 . "AcDbAlignedDimension") (cons 13 p1) (cons 14 p2)
                               (cons 50 rot) '(100 . "AcDbRotatedDimension")))))
      (if r
        (dk3s_made r)
        (setq g_dk3s_dim_mode "command")   ; entmake не прошёл — переключаемся на команду
      )
    )
  )
  (if (/= g_dk3s_dim_mode "entmake")
    (progn
      ;; запасной путь: число ставит команда (положение tp не передаётся)
      (if (= txt "")
        (command "_.DIMLINEAR" p1 p2 (if (= rot 90) "_V" "_H") pd)
        (command "_.DIMLINEAR" p1 p2 (if (= rot 90) "_V" "_H") "_T" txt pd)
      )
      (setq g_dk3s_cnt (1+ g_dk3s_cnt))
    )
  )
)

;; Размер на аксонометрии (ГОСТ 2.317): размерная линия под углом rot (параллельно измеряемому отрезку),
;; выносные линии — под углом rot + obl (параллельно аксонометрической оси); группа 52 — добавка к повороту
;; (опыт с ODA 19.09.2026: при rot 30 и obl -60 выносные легли под 150°). В приведённой изометрии длина вдоль
;; осей на листе истинная, поэтому число — автоматическое (txt ""). tp — место числа (флаг 128), как у dk3s_dim_t.
;; Запасной путь без entmake — повёрнутый размер командой, без наклона выносных.
(defun dk3s_dim_obl (p1 p2 pd rot obl txt tp / r)
  (if (= g_dk3s_dim_mode "entmake")
    (progn
      (setq r (entmake (append
                         (list '(0 . "DIMENSION") '(100 . "AcDbEntity") (cons 8 g_dk3s_lay_dim)
                               '(100 . "AcDbDimension") (cons 10 pd))
                         (if tp (list (cons 11 tp)) nil)
                         (list (cons 70 (if tp 160 32)) (cons 1 txt) (cons 3 g_dk3s_dimstyle)
                               '(100 . "AcDbAlignedDimension") (cons 13 p1) (cons 14 p2)
                               (cons 50 rot) (cons 52 obl) '(100 . "AcDbRotatedDimension")))))
      (if r
        (dk3s_made r)
        (setq g_dk3s_dim_mode "command")
      )
    )
  )
  (if (/= g_dk3s_dim_mode "entmake")
    (progn
      (command "_.DIMLINEAR" p1 p2 "_R" rot pd)
      (setq g_dk3s_cnt (1+ g_dk3s_cnt))
    )
  )
)

;; Точка tp для числа вертикального размера, вынесенного за контур на продолжение размерной линии
;; (ГОСТ 2.307, рис. 14): z — станция размерной линии, re — край детали (координата вида),
;; sgn — 1 число выше детали, -1 ниже; str — число, как его напишет CAD («O» вместо знака Ø), для длины.
;; x — сама размерная линия (DIMTMOVE 0), y — середина числа: от контура длина стрелки + 1 мм листа
;; (ближе nanoCAD число не ставит — отодвигает сам); при наружных стрелках CAD отодвинет его ещё
;; и за хвост стрелки. Число встанет слева от линии.
(defun dk3s_dimtxt_v (z re sgn str / h w p)
  (setq h (* g_dk3s_txt_h g_dk3s_scale_den)
        w (dk3s_text_w str h)
        p (dk3s_p z re))
  (list (car p)
        (+ (cadr p) (* sgn (+ (* 4.0 g_dk3s_scale_den) (/ w 2.0))))   ; стрелка 3 + 1 мм
        0.0)
)

;; То же для горизонтального размера: r — уровень размерной линии, z — выносная линия, за которую
;; выносится число, sgn — -1 влево, 1 вправо; y — сама размерная линия, число CAD поставит над ней.
(defun dk3s_dimtxt_h (z r sgn str / h w p)
  (setq h (* g_dk3s_txt_h g_dk3s_scale_den)
        w (dk3s_text_w str h)
        p (dk3s_p z r))
  (list (+ (car p) (* sgn (+ (* 4.0 g_dk3s_scale_den) (/ w 2.0))))   ; стрелка 3 + 1 мм
        (cadr p)
        0.0)
)

;; Осевая от z1 до z2 на уровне r0 с разрывами под числами вертикальных размеров, стоящими на ней
;; (ГОСТ 2.307: в месте размерного числа осевые прерывают); zs — станции размерных линий по возрастанию
(defun dk3s_axis_seg (z1 z2 r0 zs / a g1 g2 z)
  (setq a z1)
  (foreach z zs
    (setq g1 (- z (/ (* (+ 0.625 g_dk3s_txt_h 0.75) g_dk3s_scale_den) g_dk3s_k))   ; левее числа
          g2 (- z (/ (* 0.25 g_dk3s_scale_den) g_dk3s_k)))                         ; между числом и линией
    (if (and (> g1 a) (< g2 z2))
      (progn
        (dk3s_line (dk3s_p a r0) (dk3s_p g1 r0) g_dk3s_lay_axis)
        (setq a g2)
      )
    )
  )
  (dk3s_line (dk3s_p a r0) (dk3s_p z2 r0) g_dk3s_lay_axis)
)

;; Выноска: точка на детали (с точкой), излом, полка и текст над полкой
;; pt — точка на детали, ps — начало полки, dir — 1 полка вправо, -1 влево
(defun dk3s_leader (pt ps dir str / h w g pe)
  (setq h (* g_dk3s_txt_h g_dk3s_scale_den))
  (setq w (dk3s_text_w str h))                   ; ширина надписи (ГОСТ 2.304 тип Б, с запасом)
  (setq g (* 0.3 h))                             ; полка выступает за выноску: надпись не касается выноски
  ;; хвост полки 0,15h за надписью (v1.3.5): шрифтом nanoCAD (CS_Gost2304) «щ», «ш», «т», «а» шире оценки,
  ;; «Труба защитная» свисала с полки на 0,1h (проверка shelves_fit, 28.09.2026)
  (setq pe (list (+ (car ps) (* dir (+ w g (* 0.15 h)))) (cadr ps) 0.0))
  (dk3s_dot pt (* 0.5 g_dk3s_scale_den) g_dk3s_lay_thin)
  (dk3s_line pt ps g_dk3s_lay_thin)
  (dk3s_line ps pe g_dk3s_lay_thin)
  ;; надпись прижата к выноске: вправо — от левого края, влево — от правого (лишняя ширина уходит от выноски)
  (dk3s_text (list (+ (car ps) (* dir g)) (+ (cadr ps) (* 0.25 h)) 0.0)
             h str 0.0 (if (> dir 0) 0 2) g_dk3s_lay_text)
)

;;; ---------------------------------------------------------------------------
;;; 6. РАМКА И ОСНОВНАЯ НАДПИСЬ (ГОСТ 2.104, форма 1, 185x55)
;;;    Все размеры бумаги умножаются на g_dk3s_scale_den.
;;; ---------------------------------------------------------------------------

;; Линия внутри основной надписи по координатам бумаги (мм от левого нижнего угла штампа);
;; основные (толстые) линии — слой рамки, тонкие (строки по 5 мм, подграфы) — тонкий слой
(defun dk3s_tb_line (x1 y1 x2 y2)
  (dk3s_line (dk3s_ps (+ g_dk3s_tbx (* g_dk3s_scale_den x1)) (+ g_dk3s_tby (* g_dk3s_scale_den y1)))
             (dk3s_ps (+ g_dk3s_tbx (* g_dk3s_scale_den x2)) (+ g_dk3s_tby (* g_dk3s_scale_den y2)))
             g_dk3s_lay_frame)
)
(defun dk3s_tb_thin (x1 y1 x2 y2)
  (dk3s_line (dk3s_ps (+ g_dk3s_tbx (* g_dk3s_scale_den x1)) (+ g_dk3s_tby (* g_dk3s_scale_den y1)))
             (dk3s_ps (+ g_dk3s_tbx (* g_dk3s_scale_den x2)) (+ g_dk3s_tby (* g_dk3s_scale_den y2)))
             g_dk3s_lay_thin)
)

;; Текст в штампе: x,y — бумага (мм от угла штампа), h — высота на бумаге, just — как в dk3s_text
(defun dk3s_tb_text (x y h str just)
  (dk3s_text (dk3s_ps (+ g_dk3s_tbx (* g_dk3s_scale_den x)) (+ g_dk3s_tby (* g_dk3s_scale_den y)))
             (* h g_dk3s_scale_den) str 0.0 just g_dk3s_lay_text)
)

;; Текст в штампе, подогнанный по ширине: не шире maxw (мм бумаги), иначе сжатие по ширине
(defun dk3s_tb_fit (x y h str just maxw / w wf)
  (setq w (dk3s_text_w str h))
  (setq wf (if (> w maxw) (/ maxw w) 1.0))
  (dk3s_text_wf (dk3s_ps (+ g_dk3s_tbx (* g_dk3s_scale_den x)) (+ g_dk3s_tby (* g_dk3s_scale_den y)))
                (* h g_dk3s_scale_den) str 0.0 just g_dk3s_lay_text wf)
)

(defun dk3s_draw_frame ( / s w h x0 y0 x1 y1 gx0 gx1)
  (setq s g_dk3s_scale_den w (* s g_dk3s_sheet_w) h (* s g_dk3s_sheet_h))
  ;; граница листа (тонкая) и рамка (основная): поля 20 слева, 5 остальные
  (dk3s_rect (dk3s_ps 0.0 0.0) (dk3s_ps w h) g_dk3s_lay_thin)
  (setq x0 (* s 20.0) y0 (* s 5.0) x1 (- w (* s 5.0)) y1 (- h (* s 5.0)))
  (dk3s_rect (dk3s_ps x0 y0) (dk3s_ps x1 y1) g_dk3s_lay_frame)
  ;; основная надпись — правый нижний угол рамки
  (setq g_dk3s_tbx (- x1 (* s 185.0)) g_dk3s_tby y0)
  (dk3s_tb_line 0.0 0.0 0.0 55.0)  (dk3s_tb_line 0.0 55.0 185.0 55.0)
  ;; левая часть 65 мм: вертикали основные, строки по 5 тонкие, граница табл. изменений основная
  (dk3s_tb_line 65.0 0.0 65.0 55.0)
  (dk3s_tb_line 7.0 30.0 7.0 55.0)   (dk3s_tb_line 17.0 0.0 17.0 55.0)
  (dk3s_tb_line 40.0 0.0 40.0 55.0)  (dk3s_tb_line 55.0 0.0 55.0 55.0)
  (dk3s_tb_line 0.0 30.0 65.0 30.0)
  (foreach yy '(5.0 10.0 15.0 20.0 25.0 35.0 40.0 45.0 50.0) (dk3s_tb_thin 0.0 yy 65.0 yy))
  ;; правая часть 120 мм (форма 1): обозначение 120x15; наименование 70x25, материал 70x15;
  ;; справа 50 мм: Лит./Масса/Масштаб 15/17/18 (подписи 5, значения 15), Лист/Листов 20/30 (5), организация 15
  (dk3s_tb_line 65.0 40.0 185.0 40.0)   ; низ графы обозначения
  (dk3s_tb_line 65.0 15.0 135.0 15.0)   ; низ графы наименования
  (dk3s_tb_line 135.0 0.0 135.0 40.0)
  (dk3s_tb_line 135.0 35.0 185.0 35.0)  (dk3s_tb_line 135.0 20.0 185.0 20.0)
  (dk3s_tb_line 135.0 15.0 185.0 15.0)
  (dk3s_tb_line 150.0 20.0 150.0 40.0)  (dk3s_tb_line 167.0 20.0 167.0 40.0)
  (dk3s_tb_thin 140.0 20.0 140.0 35.0)  (dk3s_tb_thin 145.0 20.0 145.0 35.0)
  (dk3s_tb_line 155.0 15.0 155.0 20.0)
  ;; подписи граф 3 мм, как в чертежах ЭКОР; не входит в графу (с зазором 1 мм с каждой стороны) — сжатие по ширине, как у ЭКОР
  (dk3s_tb_fit 3.5 31.0 3.0 "Изм." 3 5.0)       (dk3s_tb_fit 12.0 31.0 3.0 "Лист" 3 8.0)
  (dk3s_tb_fit 28.5 31.0 3.0 "№ докум." 3 21.0) (dk3s_tb_fit 47.5 31.0 3.0 "Подп." 3 13.0)
  (dk3s_tb_fit 60.0 31.0 3.0 "Дата" 3 8.0)
  (dk3s_tb_fit 1.0 26.0 3.0 "Разраб." 0 15.0)   (dk3s_tb_fit 1.0 21.0 3.0 "Пров." 0 15.0)
  (dk3s_tb_fit 1.0 16.0 3.0 "Т.контр." 0 15.0)  (dk3s_tb_fit 1.0 6.0 3.0 "Н.контр." 0 15.0)
  (dk3s_tb_fit 1.0 1.0 3.0 "Утв." 0 15.0)
  (dk3s_tb_fit 142.5 36.0 3.0 "Лит." 3 13.0)    (dk3s_tb_fit 158.5 36.0 3.0 "Масса" 3 15.0)
  (dk3s_tb_fit 176.0 36.0 3.0 "Масштаб" 3 16.0)
  (dk3s_tb_fit 136.5 16.0 3.0 "Лист" 0 8.0)     (dk3s_tb_fit 156.5 16.0 3.0 "Листов" 0 12.0)
  ;; дополнительные графы (ГОСТ 2.104, форма 2): левое поле снизу вверх 25/35/25/25/35,
  ;; сверху "Перв. примен." и "Справ. №" по 60; графа обозначения 70x14 на верхней рамке
  (setq gx0 (* s 8.0) gx1 x0)
  (dk3s_line (dk3s_ps gx0 y0) (dk3s_ps gx0 (+ y0 (* s 145.0))) g_dk3s_lay_frame)
  (foreach yy '(25.0 60.0 85.0 110.0 145.0)
    (dk3s_line (dk3s_ps gx0 (+ y0 (* s yy))) (dk3s_ps gx1 (+ y0 (* s yy))) g_dk3s_lay_frame))
  (foreach g (list (list 12.5 "Инв. № подл.") (list 42.5 "Подп. и дата") (list 72.5 "Взам. инв. №")
                   (list 97.5 "Инв. № дубл.") (list 127.5 "Подп. и дата"))
    (dk3s_text (dk3s_ps (+ gx0 (* s 6.0)) (+ y0 (* s (car g)))) (* 2.5 s) (cadr g) 90.0 1 g_dk3s_lay_text))
  (dk3s_line (dk3s_ps gx0 (- y1 (* s 120.0))) (dk3s_ps gx0 y1) g_dk3s_lay_frame)
  (foreach yy '(60.0 120.0)
    (dk3s_line (dk3s_ps gx0 (- y1 (* s yy))) (dk3s_ps gx1 (- y1 (* s yy))) g_dk3s_lay_frame))
  (dk3s_text (dk3s_ps (+ gx0 (* s 6.0)) (- y1 (* s 30.0))) (* 2.5 s) "Перв. примен." 90.0 1 g_dk3s_lay_text)
  (dk3s_text (dk3s_ps (+ gx0 (* s 6.0)) (- y1 (* s 90.0))) (* 2.5 s) "Справ. №" 90.0 1 g_dk3s_lay_text)
  (dk3s_rect (dk3s_ps x0 (- y1 (* s 14.0))) (dk3s_ps (+ x0 (* s 70.0)) y1) g_dk3s_lay_frame)
  (dk3s_text (dk3s_ps (+ x0 (* s 35.0)) (- y1 (* s 7.0))) (* 5.0 s) g_dk3s_designation 180.0 1 g_dk3s_lay_text)
  ;; под основной надписью
  (dk3s_text (dk3s_ps (+ g_dk3s_tbx (* s 100.0)) (- y0 (* s 4.0))) (* 2.5 s) "Копировал" 0.0 3 g_dk3s_lay_text)
  (dk3s_text (dk3s_ps (+ g_dk3s_tbx (* s 165.0)) (- y0 (* s 4.0))) (* 2.5 s) (strcat "Формат " g_dk3s_format) 0.0 3 g_dk3s_lay_text)
  ;; содержимое граф
  (dk3s_tb_fit 125.0 45.5 5.0 g_dk3s_designation 3 116.0)
  (dk3s_tb_fit 100.0 33.5 4.0 g_dk3s_name1 3 66.0)
  (dk3s_tb_fit 100.0 26.0 4.0 g_dk3s_name2 3 66.0)
  (dk3s_tb_fit 100.0 18.5 4.0 g_dk3s_name3 3 66.0)
  (dk3s_tb_text 176.0 27.5 5.0 (strcat "1:" (rtos g_dk3s_scale_den 2 0)) 1)
  (dk3s_tb_text 148.0 16.0 3.0 "1" 0)       (dk3s_tb_text 176.0 16.0 3.0 "1" 0)
  (dk3s_tb_fit 160.0 8.5 3.5 g_dk3s_org1 3 46.0)
  (dk3s_tb_fit 160.0 3.0 3.5 g_dk3s_org2 3 46.0)
  (dk3s_tb_fit 18.0 26.0 3.0 g_dk3s_author 0 22.0)
  (dk3s_tb_fit 18.0 21.0 3.0 g_dk3s_checker 0 22.0)
)

;;; ---------------------------------------------------------------------------
;;; 7. ГЛАВНЫЙ ВИД: узлы датчика (координаты z, r — таблица параметров)
;;; ---------------------------------------------------------------------------

;; Образующие цилиндра (две продольные линии) от z1 до z2 при радиусе r, ось на r0
(defun dk3s_cyl (z1 z2 r r0)
  (dk3s_line (dk3s_p z1 (+ r0 r)) (dk3s_p z2 (+ r0 r)) g_dk3s_lay_main)
  (dk3s_line (dk3s_p z1 (- r0 r)) (dk3s_p z2 (- r0 r)) g_dk3s_lay_main)
)

;; Торцевая линия при z от r1 до r2
(defun dk3s_face (z r1 r2)
  (dk3s_line (dk3s_p z r1) (dk3s_p z r2) g_dk3s_lay_main)
)

;; Шестигранник в боковой проекции (по углам к наблюдателю: видны три грани), как в чертежах ЭКОР.
;; z1 — торец без фаски, z2 — торец с фаской 30 градусов до диаметра s; s — под ключ, e — по углам.
;; Фаска режет рёбра на глубине c = (e - s)/2 * tg30; на каждой грани — дуга через концы рёбер
;; и середину грани на торце (у гайки ЭКОР 714.541.000 так совпадает до 0,02 мм).
(defun dk3s_hex (z1 z2 s e / c zc ys)
  (setq c (* (/ (- e s) 2.0) (/ (sin (dk3s_rad 30.0)) (cos (dk3s_rad 30.0)))))
  (setq zc (if (> z2 z1) (- z2 c) (+ z2 c)))          ; конец рёбер у фаски
  (setq ys (* s (/ (sqrt 3.0) 4.0)))                   ; середина боковой грани в проекции
  (dk3s_cyl z1 zc (/ e 2.0) 0.0)                       ; крайние рёбра
  (dk3s_cyl z1 zc (/ e 4.0) 0.0)                       ; рёбра средней грани
  (dk3s_face z1 (/ e -2.0) (/ e 2.0))                  ; торец без фаски
  (dk3s_face z2 (/ s -2.0) (/ s 2.0))                  ; торец с фаской (окружность фаски = s)
  (dk3s_line (dk3s_p z2 (/ s 2.0)) (dk3s_p zc (/ e 2.0)) g_dk3s_lay_main)
  (dk3s_line (dk3s_p z2 (/ s -2.0)) (dk3s_p zc (/ e -2.0)) g_dk3s_lay_main)
  (dk3s_arc3 (dk3s_p zc (/ e -4.0)) (dk3s_p z2 0.0) (dk3s_p zc (/ e 4.0)) g_dk3s_lay_main)
  (dk3s_arc3 (dk3s_p zc (/ e 4.0)) (dk3s_p z2 ys) (dk3s_p zc (/ e 2.0)) g_dk3s_lay_main)
  (dk3s_arc3 (dk3s_p zc (/ e -2.0)) (dk3s_p z2 (- ys)) (dk3s_p zc (/ e -4.0)) g_dk3s_lay_main)
  e
)

;; Разъём-штырь токоотвода: буртик, корпус, штырь с острием; z0 — начало, r0 — ось
(defun dk3s_connector (z0 r0 / z1 z2 z3 z4 rp)
  (setq z1 (+ z0 g_dk3s_conn_collar_l) z2 (+ z1 g_dk3s_conn_body_l)
        z3 (+ z2 1.0 g_dk3s_conn_pin_l) z4 (+ z3 g_dk3s_conn_tip_l) rp (/ g_dk3s_conn_pin_d 2.0))
  (dk3s_face z0 (- r0 (/ g_dk3s_conn_collar_d 2.0)) (+ r0 (/ g_dk3s_conn_collar_d 2.0)))
  (dk3s_cyl z0 z1 (/ g_dk3s_conn_collar_d 2.0) r0)
  (dk3s_face z1 (- r0 (/ g_dk3s_conn_collar_d 2.0)) (+ r0 (/ g_dk3s_conn_collar_d 2.0)))
  (dk3s_cyl z1 z2 (/ g_dk3s_conn_body_d 2.0) r0)
  (dk3s_face z2 (- r0 (/ g_dk3s_conn_body_d 2.0)) (+ r0 (/ g_dk3s_conn_body_d 2.0)))
  (dk3s_cyl z2 z3 rp r0)
  (dk3s_line (dk3s_p z3 (+ r0 rp)) (dk3s_p z4 (+ r0 (* 0.4 rp))) g_dk3s_lay_main)
  (dk3s_line (dk3s_p z3 (- r0 rp)) (dk3s_p z4 (- r0 (* 0.4 rp))) g_dk3s_lay_main)
  (dk3s_face z4 (- r0 (* 0.4 rp)) (+ r0 (* 0.4 rp)))
  z4
)

;; Скоба (П-образная, проволока Ø2) с центральной перемычкой — как на монтажном чертеже
(defun dk3s_draw_guard ( / w2 d ro ri zs zc)
  (setq w2 (/ g_dk3s_guard_w 2.0) d g_dk3s_guard_d ro g_dk3s_guard_r ri (- ro d) zs g_dk3s_z_sleeve zc ro)
  ;; наружный контур
  (dk3s_line (dk3s_p zs w2) (dk3s_p zc w2) g_dk3s_lay_main)
  (dk3s_arc (dk3s_p zc (- w2 ro)) (dk3s_l ro) 90.0 180.0 g_dk3s_lay_main)
  (dk3s_line (dk3s_p 0.0 (- w2 ro)) (dk3s_p 0.0 (- ro w2)) g_dk3s_lay_main)
  (dk3s_arc (dk3s_p zc (- ro w2)) (dk3s_l ro) 180.0 270.0 g_dk3s_lay_main)
  (dk3s_line (dk3s_p zc (- w2)) (dk3s_p zs (- w2)) g_dk3s_lay_main)
  ;; внутренний контур
  (dk3s_line (dk3s_p zs (- w2 d)) (dk3s_p zc (- w2 d)) g_dk3s_lay_main)
  (dk3s_arc (dk3s_p zc (- w2 ro)) (dk3s_l ri) 90.0 180.0 g_dk3s_lay_main)
  (dk3s_line (dk3s_p d (- w2 ro)) (dk3s_p d (- ro w2)) g_dk3s_lay_main)
  (dk3s_arc (dk3s_p zc (- ro w2)) (dk3s_l ri) 180.0 270.0 g_dk3s_lay_main)
  (dk3s_line (dk3s_p zc (- d w2)) (dk3s_p zs (- d w2)) g_dk3s_lay_main)
  ;; центральная перемычка
  (dk3s_cyl d zs (/ d 2.0) 0.0)
)

;; Наконечник с рабочим электродом (видимая часть над торцом гильзы), ось смещена
(defun dk3s_draw_tip_main ( / r0 zh zc zn zw rt rn e)
  (setq r0 g_dk3s_tip_off rt (/ g_dk3s_tip_d 2.0) rn (/ g_dk3s_tip_nose_d 2.0))
  (setq zh (- g_dk3s_z_sleeve g_dk3s_tip_vis) zc (- zh g_dk3s_tip_cone) zw (- zc g_dk3s_we_len))
  (setq e (/ g_dk3s_tip_s (cos (dk3s_rad 30.0))))
  ;; шестигранная часть (видимая)
  (dk3s_cyl zh g_dk3s_z_sleeve rt r0)
  (dk3s_cyl zh g_dk3s_z_sleeve (/ e 4.0) r0)
  (dk3s_face zh (- r0 rt) (+ r0 rt))
  ;; конус
  (dk3s_line (dk3s_p zh (+ r0 rt)) (dk3s_p zc (+ r0 rn)) g_dk3s_lay_main)
  (dk3s_line (dk3s_p zh (- r0 rt)) (dk3s_p zc (- r0 rn)) g_dk3s_lay_main)
  (dk3s_face zc (- r0 rn) (+ r0 rn))
  ;; рабочий электрод Ø1,4, выступ 2
  (dk3s_cyl zw zc (/ g_dk3s_we_d 2.0) r0)
  (dk3s_face zw (- r0 (/ g_dk3s_we_d 2.0)) (+ r0 (/ g_dk3s_we_d 2.0)))
)

;; Защитная гильза с перфорацией
(defun dk3s_draw_sleeve ( / r i z rs a b)
  (setq r (/ g_dk3s_sleeve_d 2.0))
  (dk3s_face g_dk3s_z_sleeve (- r) r)
  (dk3s_cyl g_dk3s_z_sleeve g_dk3s_z_shell r 0.0)
  ;; фронтальный ряд отверстий
  (setq i 0)
  (repeat g_dk3s_hole_n
    (setq z (+ g_dk3s_hole_z1 (* i g_dk3s_hole_pitch)))
    (dk3s_circle (dk3s_p z 0.0) (dk3s_l (/ g_dk3s_hole_d 2.0)) g_dk3s_lay_main)
    (setq i (1+ i))
  )
  ;; боковые отверстия (в шахматном порядке) — видны как эллипсы на образующих
  (setq rs (* r (sin (dk3s_rad 25.0))))          ; удаление центра от образующей ~0,42R
  (setq a (/ g_dk3s_hole_d 2.0) b (* (/ g_dk3s_hole_d 2.0) (cos (dk3s_rad 60.0))))
  (setq i 0)
  (repeat g_dk3s_hole_side_n
    (setq z (+ g_dk3s_hole_z1 (/ g_dk3s_hole_pitch 2.0) (* i g_dk3s_hole_pitch)))
    (dk3s_ellipse (dk3s_p z (- r rs)) (dk3s_l a) (dk3s_l b) g_dk3s_lay_main)
    (dk3s_ellipse (dk3s_p z (- rs r)) (dk3s_l a) (dk3s_l b) g_dk3s_lay_main)
    (setq i (1+ i))
  )
)

;; Корпус с резьбой, фланец, сальниковая втулка (шестигранники), шейка, бирка
(defun dk3s_draw_gland ( / rs rr rp e1 e2 rc rg rn rst zsh d1 h)
  (setq rs (/ g_dk3s_shell_d 2.0) rr (/ g_dk3s_relief_d 2.0) rp (/ g_dk3s_plate_d 2.0))
  ;; корпус M42x3: торец с фаской, наружный диаметр, внутренний диаметр резьбы (тонкая)
  (setq zsh (+ g_dk3s_z_shell g_dk3s_shell_ch))
  (dk3s_face g_dk3s_z_shell (- (/ g_dk3s_sleeve_d 2.0)) (- (- rs g_dk3s_shell_ch)))
  (dk3s_face g_dk3s_z_shell (/ g_dk3s_sleeve_d 2.0) (- rs g_dk3s_shell_ch))
  (dk3s_line (dk3s_p g_dk3s_z_shell (- rs g_dk3s_shell_ch)) (dk3s_p zsh rs) g_dk3s_lay_main)
  (dk3s_line (dk3s_p g_dk3s_z_shell (- g_dk3s_shell_ch rs)) (dk3s_p zsh (- rs)) g_dk3s_lay_main)
  (dk3s_cyl zsh g_dk3s_z_relief rs 0.0)
  (setq d1 (- g_dk3s_shell_d (* 1.0825 g_dk3s_thread_pitch)))   ; внутренний диаметр резьбы
  (dk3s_line (dk3s_p zsh (/ d1 2.0)) (dk3s_p g_dk3s_z_relief (/ d1 2.0)) g_dk3s_lay_thin)
  (dk3s_line (dk3s_p zsh (/ d1 -2.0)) (dk3s_p g_dk3s_z_relief (/ d1 -2.0)) g_dk3s_lay_thin)
  ;; проточка
  (dk3s_face g_dk3s_z_relief (- rs) rs)
  (dk3s_cyl g_dk3s_z_relief g_dk3s_z_plate rr 0.0)
  ;; фланец-пластина
  (dk3s_face g_dk3s_z_plate (- rp) rp)
  (dk3s_cyl g_dk3s_z_plate g_dk3s_z_hex1 rp 0.0)
  (dk3s_face g_dk3s_z_hex1 (- rp) rp)
  ;; шестигранник S46 корпуса: фаска 30° со стороны гайки, дуги на гранях (как у ЭКОР)
  (setq e1 (dk3s_hex g_dk3s_z_hex1 g_dk3s_z_cyl g_dk3s_hex1_s g_dk3s_hex1_e))
  ;; видимая резьба M33x2 гайки нажимной (наружный Ø33, внутренний - тонкая линия) и канавка Ø30
  (setq rc (/ g_dk3s_cyl_d 2.0) rg (/ g_dk3s_groove_d 2.0))
  (dk3s_cyl g_dk3s_z_cyl g_dk3s_z_groove rc 0.0)
  (setq d1 (- g_dk3s_cyl_d (* 1.0825 g_dk3s_thread2_pitch)))
  (dk3s_line (dk3s_p g_dk3s_z_cyl (/ d1 2.0)) (dk3s_p g_dk3s_z_groove (/ d1 2.0)) g_dk3s_lay_thin)
  (dk3s_line (dk3s_p g_dk3s_z_cyl (/ d1 -2.0)) (dk3s_p g_dk3s_z_groove (/ d1 -2.0)) g_dk3s_lay_thin)
  (dk3s_face g_dk3s_z_groove (- rc) rc)
  (dk3s_cyl g_dk3s_z_groove g_dk3s_z_hex2 rg 0.0)
  ;; шестигранник S36 гайки нажимной: фаска 30° с наружного торца
  (setq e2 (dk3s_hex g_dk3s_z_hex2 g_dk3s_z_neck g_dk3s_hex2_s g_dk3s_hex2_e))
  ;; шейка Ø20,8, ступень Ø18,8, конус Ø16 -> Ø15,4
  (setq rn (/ g_dk3s_neck_d 2.0) rst (/ g_dk3s_step_d 2.0))
  (dk3s_cyl g_dk3s_z_neck g_dk3s_z_step rn 0.0)
  (dk3s_face g_dk3s_z_step (- rn) rn)
  (dk3s_cyl g_dk3s_z_step g_dk3s_z_taper rst 0.0)
  (dk3s_face g_dk3s_z_taper (- rst) rst)
  (dk3s_line (dk3s_p g_dk3s_z_taper (/ g_dk3s_taper_d1 2.0)) (dk3s_p g_dk3s_z_tag (/ g_dk3s_taper_d2 2.0)) g_dk3s_lay_main)
  (dk3s_line (dk3s_p g_dk3s_z_taper (/ g_dk3s_taper_d1 -2.0)) (dk3s_p g_dk3s_z_tag (/ g_dk3s_taper_d2 -2.0)) g_dk3s_lay_main)
  ;; бирка с заводским номером (16 x 10) и логотип
  (dk3s_rect (dk3s_p g_dk3s_z_tag (/ g_dk3s_tag_w -2.0)) (dk3s_p g_dk3s_z_tag_end (/ g_dk3s_tag_w 2.0)) g_dk3s_lay_main)
  (setq h (dk3s_l 4.0))
  (dk3s_text (dk3s_p (/ (+ g_dk3s_z_tag g_dk3s_z_tag_end) 2.0) 0.0) h "ЭК" 0.0 1 g_dk3s_lay_text)
)

;; Трубка токоотвода РЭ Ø6, мостики, хомуты и разъём WE
(defun dk3s_draw_bundle ( / rt rb z1 z2 zc1 zc2 rc)
  (setq rt (/ g_dk3s_tube_d 2.0) rb (+ g_dk3s_bridge_r (/ g_dk3s_bridge_d 2.0)))
  (setq zc1 g_dk3s_z_clamp1 zc2 g_dk3s_z_clamp2 rc (/ g_dk3s_clamp_d 2.0))
  ;; трубка Ø6 сегментами между хомутами
  (dk3s_cyl g_dk3s_z_tag_end zc1 rt 0.0)
  (dk3s_cyl (+ zc1 g_dk3s_clamp_len) zc2 rt 0.0)
  (dk3s_cyl (+ zc2 g_dk3s_clamp_len) g_dk3s_z_we_end rt 0.0)
  ;; наружные образующие мостиков (внутренние совпадают с трубкой)
  (dk3s_line (dk3s_p g_dk3s_z_tag_end rb) (dk3s_p zc1 rb) g_dk3s_lay_main)
  (dk3s_line (dk3s_p g_dk3s_z_tag_end (- rb)) (dk3s_p zc1 (- rb)) g_dk3s_lay_main)
  (dk3s_line (dk3s_p (+ zc1 g_dk3s_clamp_len) rb) (dk3s_p zc2 rb) g_dk3s_lay_main)
  (dk3s_line (dk3s_p (+ zc1 g_dk3s_clamp_len) (- rb)) (dk3s_p zc2 (- rb)) g_dk3s_lay_main)
  (dk3s_line (dk3s_p (+ zc2 g_dk3s_clamp_len) rb) (dk3s_p g_dk3s_z_bend rb) g_dk3s_lay_main)
  (dk3s_line (dk3s_p (+ zc2 g_dk3s_clamp_len) (- rb)) (dk3s_p g_dk3s_z_bend (- rb)) g_dk3s_lay_main)
  ;; хомуты
  (dk3s_rect (dk3s_p zc1 (- rc)) (dk3s_p (+ zc1 g_dk3s_clamp_len) rc) g_dk3s_lay_main)
  (dk3s_rect (dk3s_p zc2 (- rc)) (dk3s_p (+ zc2 g_dk3s_clamp_len) rc) g_dk3s_lay_main)
  ;; разъём токоотвода рабочего электрода
  (dk3s_connector g_dk3s_z_we_end 0.0)
)

;; Провод токоотвода вспомогательного электрода с разъёмом
(defun dk3s_draw_se ( / r0 rw)
  (setq r0 g_dk3s_se_r rw (/ g_dk3s_se_d 2.0))
  (dk3s_cyl g_dk3s_z_se_start g_dk3s_z_se_end rw r0)
  (dk3s_connector g_dk3s_z_se_end r0)
)

;; S-образный изгиб мостика: от (z1, r1) к (z2, r2), касательные вдоль оси;
;; рисуются две образующие на расстоянии ±rb/2 от осевой линии. Мостик лежит за трубкой РЭ: внутренняя
;; образующая первой дуги у начала закрыта трубкой и разъёмом РЭ и рисуется только с |r| >= rh
(defun dk3s_draw_bend (z1 r1 z2 r2 rb rh / dx dy R th sgn c1 c2 a1 a2 hb cs ps)
  (setq dx (- z2 z1) dy (- r2 r1) sgn (if (< dy 0.0) -1.0 1.0) dy (abs dy) hb (/ rb 2.0))
  (setq R (/ (+ (* dx dx) (* dy dy)) (* 4.0 dy)))
  (setq th (dk3s_deg (atan (/ dx 2.0) (- R (/ dy 2.0)))))
  ;; угол поворота по первой дуге, с которого внутренняя образующая выходит из-за разъёма: |r| = rh
  (setq cs (/ (+ R (abs r1) (- rh)) (+ R hb)))
  (setq ps (if (>= cs 1.0) 0.0 (dk3s_deg (atan (sqrt (- 1.0 (* cs cs))) cs))))
  ;; первая дуга: центр над началом (по направлению sgn), от 270° до 270°+th (при sgn>0)
  (setq c1 (dk3s_p z1 (+ r1 (* sgn R))) c2 (dk3s_p z2 (- r2 (* sgn R))))
  (if (> sgn 0.0)
    (progn
      (dk3s_arc c1 (dk3s_l (- R hb)) 270.0 (+ 270.0 th) g_dk3s_lay_main)
      (if (< ps th) (dk3s_arc c1 (dk3s_l (+ R hb)) (+ 270.0 ps) (+ 270.0 th) g_dk3s_lay_main))
      (dk3s_arc c2 (dk3s_l (- R hb)) 90.0 (+ 90.0 th) g_dk3s_lay_main)
      (dk3s_arc c2 (dk3s_l (+ R hb)) 90.0 (+ 90.0 th) g_dk3s_lay_main)
    )
    (progn
      (dk3s_arc c1 (dk3s_l (- R hb)) (- 90.0 th) 90.0 g_dk3s_lay_main)
      (if (< ps th) (dk3s_arc c1 (dk3s_l (+ R hb)) (- 90.0 th) (- 90.0 ps) g_dk3s_lay_main))
      (dk3s_arc c2 (dk3s_l (- R hb)) (- 270.0 th) 270.0 g_dk3s_lay_main)
      (dk3s_arc c2 (dk3s_l (+ R hb)) (- 270.0 th) 270.0 g_dk3s_lay_main)
    )
  )
)

;; Электрод сравнения на оси r0 (два сегмента, перемычка, штырь)
(defun dk3s_draw_re (r0 / r rn z1 z2 z3 z4)
  (setq r (/ g_dk3s_re_d 2.0) rn (/ g_dk3s_re_neck_d 2.0))
  (setq z1 g_dk3s_z_re z2 (+ z1 g_dk3s_re_seg1) z3 (+ z2 g_dk3s_re_neck) z4 (+ z3 g_dk3s_re_seg2))
  (dk3s_face z1 (- r0 r) (+ r0 r))
  (dk3s_cyl z1 z2 r r0)
  (dk3s_face z2 (- r0 r) (+ r0 r))
  (dk3s_cyl z2 z3 rn r0)
  (dk3s_face z3 (- r0 r) (+ r0 r))
  (dk3s_cyl z3 z4 r r0)
  (dk3s_face z4 (- r0 r) (+ r0 r))
  ;; зазор 1 мм до буртика штыря (Ø корпуса разъёма)
  (dk3s_cyl z4 (+ z4 g_dk3s_re_gap) (/ g_dk3s_conn_body_d 2.0) r0)
  (dk3s_connector (+ z4 g_dk3s_re_gap) r0)
  ;; осевая электрода
  (dk3s_line (dk3s_p (- z1 5.0) r0) (dk3s_p (+ g_dk3s_z_total 4.0) r0) g_dk3s_lay_axis)
)

;; Осевая линия датчика
;; Ось датчика; прерывается на бирке (надпись на ней) и под числами Ø32 и M42x3
(defun dk3s_draw_axis ()
  (dk3s_axis_seg -6.0 g_dk3s_z_tag 0.0 (list g_dk3s_zdim_sleeve g_dk3s_zdim_thread))
  (dk3s_line (dk3s_p g_dk3s_z_tag_end 0.0)
             (dk3s_p (+ g_dk3s_z_we_end g_dk3s_conn_collar_l g_dk3s_conn_body_l
                        1.0 g_dk3s_conn_pin_l g_dk3s_conn_tip_l 5.0) 0.0) g_dk3s_lay_axis)
)

(defun dk3s_draw_main_view ()
  (dk3s_draw_axis)
  (dk3s_draw_guard)
  (dk3s_draw_tip_main)
  (dk3s_draw_sleeve)
  (dk3s_draw_gland)
  (dk3s_draw_bundle)
  (dk3s_draw_se)
  (dk3s_draw_bend g_dk3s_z_bend g_dk3s_bridge_r g_dk3s_z_re g_dk3s_re_r g_dk3s_bridge_d (/ g_dk3s_conn_collar_d 2.0))
  (dk3s_draw_bend g_dk3s_z_bend (- g_dk3s_bridge_r) g_dk3s_z_re (- g_dk3s_re_r) g_dk3s_bridge_d (/ g_dk3s_conn_collar_d 2.0))
  (dk3s_draw_re g_dk3s_re_r)
  (dk3s_draw_re (- g_dk3s_re_r))
)

;;; ---------------------------------------------------------------------------
;;; 8. ВЫНОСНОЙ ЭЛЕМЕНТ А (2:1): узел рабочего электрода — как Fig. 4 описания K1.
;;;    Локальная ось z' — вдоль токоотвода (0 — начало защитной трубки), r' — от оси.
;;;    Разрез: защитная трубка и наконечник заштрихованы, стержни — без штриховки.
;;; ---------------------------------------------------------------------------

(defun dk3s_draw_detail_a ( / rt rti rtap rtapm rtip rn rw rsh zt zs zh zc zw zb ztc1 ztc2 rzb hp hpt h sgn)
  ;; Узел рабочего электрода по Fig. 4 «Технического описания K1» (стр. 48): трубка и наконечник —
  ;; фторопласт (штриховка «в клетку», ГОСТ 2.306); трубка надета с натягом на хвостовик наконечника;
  ;; наконечник накручен на токоотвод M3x0,5; токоотвод на конце конусом переходит в электрод Ø1,4.
  (setq rt (/ g_dk3s_tube_d 2.0) rti (- rt g_dk3s_tube_wall) rtap (/ g_dk3s_tap_d 2.0)
        rtapm (/ g_dk3s_tap_minor_d 2.0) rtip (/ g_dk3s_tip_d 2.0) rn (/ g_dk3s_tip_nose_d 2.0)
        rw (/ g_dk3s_we_d 2.0) rsh (/ g_dk3s_tip_shank_d 2.0))
  (setq zt 22.0)                                        ; торец тела наконечника = конец трубки
  (setq zs (- zt g_dk3s_tip_shank_l))                   ; начало хвостовика (внутри трубки)
  (setq zh (+ zt g_dk3s_tip_len))                       ; конец тела Ø7 (цилиндр + шестигранник)
  (setq zc (+ zh g_dk3s_tip_cone))                      ; торец носика
  (setq zw (+ zc g_dk3s_we_len))                        ; конец электрода
  (setq zb (+ zt g_dk3s_tip_bore_end))                  ; дно отверстия Ø3, дальше канал электрода
  (setq ztc1 (+ zt g_dk3s_tap_cone_z1) ztc2 (+ zt g_dk3s_tap_cone_z2))   ; конус на конце токоотвода
  (setq rzb (- rtip (* (- zb zh) (/ (- rtip rn) g_dk3s_tip_cone))))     ; радиус наружного конуса у дна отверстия
  (setq hp (* 1.2 g_dk3s_scale_den) hpt (* 0.8 g_dk3s_scale_den))       ; шаг «клетки»: наконечник, трубка
  ;; осевая
  (dk3s_line (dk3s_p -4.0 0.0) (dk3s_p (+ zw 4.0) 0.0) g_dk3s_lay_axis)
  (foreach sgn '(1.0 -1.0)
    ;; защитная трубка: наружная и внутренняя образующие (внутренняя от хвостовика — граница натяга)
    (dk3s_line (dk3s_p 0.0 (* sgn rt)) (dk3s_p zt (* sgn rt)) g_dk3s_lay_main)
    (dk3s_line (dk3s_p 0.0 (* sgn rti)) (dk3s_p zt (* sgn rti)) g_dk3s_lay_main)
    ;; наконечник: торец хвостовика, торец тела, тело Ø7, конус, торец носика
    (dk3s_line (dk3s_p zs (* sgn rtap)) (dk3s_p zs (* sgn rsh)) g_dk3s_lay_main)
    (dk3s_line (dk3s_p zt (* sgn rsh)) (dk3s_p zt (* sgn rtip)) g_dk3s_lay_main)
    (dk3s_line (dk3s_p zt (* sgn rtip)) (dk3s_p zh (* sgn rtip)) g_dk3s_lay_main)
    (dk3s_line (dk3s_p zh (* sgn rtip)) (dk3s_p zc (* sgn rn)) g_dk3s_lay_main)
    (dk3s_line (dk3s_p zc (* sgn rw)) (dk3s_p zc (* sgn rn)) g_dk3s_lay_main)
    ;; отверстие Ø3 (по нему токоотвод) и его дно; канал электрода в носике — по электроду
    (dk3s_line (dk3s_p zs (* sgn rtap)) (dk3s_p zb (* sgn rtap)) g_dk3s_lay_main)
    (dk3s_line (dk3s_p zb (* sgn rw)) (dk3s_p zb (* sgn rtap)) g_dk3s_lay_main)
    ;; токоотвод Ø3 (не рассекается): в трубке до хвостовика, резьба — тонкая линия, конус к электроду
    (dk3s_line (dk3s_p 0.0 (* sgn rtap)) (dk3s_p zs (* sgn rtap)) g_dk3s_lay_main)
    (dk3s_line (dk3s_p 0.0 (* sgn rtapm)) (dk3s_p ztc1 (* sgn rtapm)) g_dk3s_lay_thin)
    (dk3s_line (dk3s_p ztc1 (* sgn rtap)) (dk3s_p ztc2 (* sgn rw)) g_dk3s_lay_main)
    ;; рабочий электрод Ø1,4 (приварен к токоотводу)
    (dk3s_line (dk3s_p ztc2 (* sgn rw)) (dk3s_p zw (* sgn rw)) g_dk3s_lay_main)
    ;; штриховка «в клетку»: трубка мельче, наконечник крупнее (смежные детали)
    (dk3s_hatch_cross (list (dk3s_p 0.0 (* sgn rti)) (dk3s_p zt (* sgn rti))
                            (dk3s_p zt (* sgn rt)) (dk3s_p 0.0 (* sgn rt))) hpt g_dk3s_lay_thin)
    (dk3s_hatch_cross (list (dk3s_p zs (* sgn rtap)) (dk3s_p zt (* sgn rtap))
                            (dk3s_p zt (* sgn rsh)) (dk3s_p zs (* sgn rsh))) hp g_dk3s_lay_thin)
    (dk3s_hatch_cross (list (dk3s_p zt (* sgn rtap)) (dk3s_p zh (* sgn rtap))
                            (dk3s_p zh (* sgn rtip)) (dk3s_p zt (* sgn rtip))) hp g_dk3s_lay_thin)
    (dk3s_hatch_cross (list (dk3s_p zh (* sgn rtap)) (dk3s_p zb (* sgn rtap))
                            (dk3s_p zb (* sgn rzb)) (dk3s_p zh (* sgn rtip))) hp g_dk3s_lay_thin)
    (dk3s_hatch_cross (list (dk3s_p zb (* sgn rw)) (dk3s_p zc (* sgn rw))
                            (dk3s_p zc (* sgn rn)) (dk3s_p zb (* sgn rzb))) hp g_dk3s_lay_thin)
  )
  ;; линия обрыва трубки и токоотвода слева (упрощённо — ломаная)
  (dk3s_pline (list (dk3s_p 0.0 (+ rt 0.5)) (dk3s_p -0.6 (* 0.5 rt)) (dk3s_p 0.6 0.0)
                    (dk3s_p -0.6 (* -0.5 rt)) (dk3s_p 0.0 (- -0.5 rt))) nil 0.0 g_dk3s_lay_thin)
  (dk3s_face zw (- rw) rw)
  ;; размеры выносного элемента (текст задан явно — вид увеличен)
  (setq h (* g_dk3s_txt_h g_dk3s_scale_den))
  ;; числа диаметров — над деталью на продолжении размерной линии: внутри легли бы на линии
  ;; токоотвода и отверстия (ГОСТ 2.307: размерное число не пересекают никакие линии)
  (dk3s_dim_t (dk3s_p zw rw) (dk3s_p zw (- rw)) (dk3s_p (+ zw 3.0) 0.0) 90.0
              (strcat "%%c" (dk3s_num g_dk3s_we_d 1))
              (dk3s_dimtxt_v (+ zw 3.0) rw 1.0 (strcat "O" (dk3s_num g_dk3s_we_d 1))))
  (dk3s_dim (dk3s_p zc (- rn)) (dk3s_p zw (- rn)) (dk3s_p 0.0 (- (- rtip) 3.0)) 0.0
            (dk3s_num g_dk3s_we_len 0))
  (dk3s_dim_t (dk3s_p 4.5 rt) (dk3s_p 4.5 (- rt)) (dk3s_p 4.5 0.0) 90.0
              (strcat "%%c" (dk3s_num g_dk3s_tube_d 0))              ; резьба токоотвода M3x0,5 — в ТТ, п. 3
              (dk3s_dimtxt_v 4.5 rt 1.0 (strcat "O" (dk3s_num g_dk3s_tube_d 0))))
  (dk3s_dim_t (dk3s_p (+ zt 8.0) rtip) (dk3s_p (+ zt 8.0) (- rtip)) (dk3s_p (+ zt 8.0) 0.0) 90.0
              (strcat "%%c" (dk3s_num g_dk3s_tip_d 0))
              (dk3s_dimtxt_v (+ zt 8.0) rtip 1.0 (strcat "O" (dk3s_num g_dk3s_tip_d 0))))
  (dk3s_dim (dk3s_p zs rt) (dk3s_p zt rt) (dk3s_p 0.0 (+ rtip 2.5)) 0.0
            (dk3s_num g_dk3s_tip_shank_l 0))
  ;; надписи выносного элемента
  (dk3s_leader (dk3s_p 1.0 rt) (dk3s_p -2.0 (+ rtip 7.5)) 1 "Трубка токоотвода")
  (dk3s_leader (dk3s_p (+ zt 12.0) (- rtip)) (dk3s_p (+ zt 14.0) (- (- rtip) 7.0)) 1 "Наконечник")
  (dk3s_leader (dk3s_p (+ zc 1.0) rw) (dk3s_p (+ zc 2.0) (+ rtip 7.5)) 1 "Электрод рабочий")
  (dk3s_leader (dk3s_p 6.5 (- rtap)) (dk3s_p 10.0 (- (- rtip) 13.0)) 1 "Токоотвод рабочего электрода")
  ;; заголовок вида
  (dk3s_text (dk3s_p (/ zw 2.0) (+ rtip 16.0)) (* h 1.4) "А (2:1)" 0.0 3 g_dk3s_lay_text)
  (dk3s_line (dk3s_p (- (/ zw 2.0) 7.0) (+ rtip 15.2)) (dk3s_p (+ (/ zw 2.0) 7.0) (+ rtip 15.2)) g_dk3s_lay_thin)
)

;;; ---------------------------------------------------------------------------
;;; 9. РАЗМЕРЫ, ВЫНОСКИ И ТЕХНИЧЕСКИЕ ТРЕБОВАНИЯ ГЛАВНОГО ВИДА
;;;    Размерные точки берутся из таблицы параметров — значения вычисляются CAD.
;;; ---------------------------------------------------------------------------

(defun dk3s_draw_dims_main ( / rs re rp zre1 zre2 y1 y2 y3 y4 zpl)
  (setq rs (/ g_dk3s_sleeve_d 2.0) re (/ g_dk3s_re_d 2.0) rp (/ g_dk3s_plate_d 2.0))
  (setq y1 -40.0 y2 -56.0 y3 -70.0 y4 -84.0)       ; уровни горизонтальных размеров (снизу)
  ;; перфорация: первое отверстие от вершины скобы и шаг
  ;; первое отверстие: между выносными число пересекла бы выносная размера гильзы — оно левее скобы
  (dk3s_dim_t (dk3s_p 0.0 0.0) (dk3s_p g_dk3s_hole_z1 0.0) (dk3s_p 0.0 y1) 0.0 ""
              (dk3s_dimtxt_h 0.0 y1 -1.0 (dk3s_num g_dk3s_hole_z1 1)))
  (dk3s_dim (dk3s_p g_dk3s_hole_z1 0.0) (dk3s_p (+ g_dk3s_hole_z1 g_dk3s_hole_pitch) 0.0) (dk3s_p 0.0 y1) 0.0 "")
  (dk3s_dim (dk3s_p (+ g_dk3s_hole_z1 g_dk3s_hole_pitch) 0.0)
            (dk3s_p (+ g_dk3s_hole_z1 (* 2.0 g_dk3s_hole_pitch)) 0.0) (dk3s_p 0.0 y1) 0.0 "")
  ;; длина гильзы; вершина скобы -> низ фланца; низ фланца -> штыри; общая длина
  (dk3s_dim (dk3s_p g_dk3s_z_sleeve (- rs)) (dk3s_p g_dk3s_z_shell (- rs)) (dk3s_p 0.0 y2) 0.0 "")
  (setq zpl g_dk3s_z_hex1)
  (dk3s_dim (dk3s_p 0.0 0.0) (dk3s_p zpl (- rp)) (dk3s_p 0.0 y3) 0.0 "")
  (dk3s_dim (dk3s_p zpl (- rp)) (dk3s_p g_dk3s_z_total (- g_dk3s_re_r)) (dk3s_p 0.0 y3) 0.0 "")
  (dk3s_dim (dk3s_p 0.0 0.0) (dk3s_p g_dk3s_z_total (- g_dk3s_re_r)) (dk3s_p 0.0 y4) 0.0 "*<>")
  ;; высота скобы (сверху)
  (dk3s_dim (dk3s_p 0.0 (/ g_dk3s_guard_w 2.0)) (dk3s_p g_dk3s_z_sleeve (/ g_dk3s_guard_w 2.0))
            (dk3s_p 0.0 42.0) 0.0 "")
  ;; диаметры: гильза и присоединительная резьба M42x3 корпуса
  (dk3s_dim (dk3s_p g_dk3s_zdim_sleeve rs) (dk3s_p g_dk3s_zdim_sleeve (- rs)) (dk3s_p g_dk3s_zdim_sleeve 0.0) 90.0
            "%%c<>")
  (dk3s_dim (dk3s_p g_dk3s_zdim_thread (/ g_dk3s_shell_d 2.0)) (dk3s_p g_dk3s_zdim_thread (/ g_dk3s_shell_d -2.0))
            (dk3s_p g_dk3s_zdim_thread 0.0) 90.0 (strcat "M<>x" (dk3s_num g_dk3s_thread_pitch 0)))
  ;; размеры корпуса и гайки нажимной (Ø59, S46, M33x2, S36, Ø20,8) на общем виде не ставятся —
  ;; они на чертежах деталей 714.761.000 и 714.541.000 (решение 19.09.2026)
  (dk3s_dim (dk3s_p g_dk3s_z_shell (/ g_dk3s_shell_d -2.0)) (dk3s_p g_dk3s_z_cyl (/ g_dk3s_hex1_s -2.0)) (dk3s_p 0.0 -40.0) 0.0 "")
  ;; Ø6 трубки и Ø3 провода: между выносными число легло бы на линии — выносится за контур.
  ;; Трубка идёт между двумя мостиками, поэтому число Ø6 — за мостиком (над верхним);
  ;; Ø3 — под проводом (над ним до мостика тесно: число отодвигается за стрелку и её хвост)
  (dk3s_dim_t (dk3s_p g_dk3s_zdim_tube (/ g_dk3s_tube_d 2.0)) (dk3s_p g_dk3s_zdim_tube (/ g_dk3s_tube_d -2.0))
              (dk3s_p g_dk3s_zdim_tube 0.0) 90.0 "%%c<>"
              (dk3s_dimtxt_v g_dk3s_zdim_tube (+ g_dk3s_bridge_r (/ g_dk3s_bridge_d 2.0)) 1.0
                             (strcat "O" (dk3s_num g_dk3s_tube_d 0))))
  (dk3s_dim_t (dk3s_p g_dk3s_zdim_wire (+ g_dk3s_se_r (/ g_dk3s_se_d 2.0)))
              (dk3s_p g_dk3s_zdim_wire (- g_dk3s_se_r (/ g_dk3s_se_d 2.0)))
              (dk3s_p g_dk3s_zdim_wire g_dk3s_se_r) 90.0 "%%c<>"
              (dk3s_dimtxt_v g_dk3s_zdim_wire (- g_dk3s_se_r (/ g_dk3s_se_d 2.0)) -1.0
                             (strcat "O" (dk3s_num g_dk3s_se_d 0))))
  ;; электроды сравнения: диаметр, длина, расстояние между осями
  (setq zre1 g_dk3s_z_re zre2 g_dk3s_z_re_end)
  ;; Ø20: число над верхним электродом (внутри корпуса оно во всю высоту, стрелки уходят наружу);
  ;; длина 61,1 — между электродами, выносные от нижних углов верхнего
  (dk3s_dim_t (dk3s_p g_dk3s_zdim_re (+ g_dk3s_re_r re)) (dk3s_p g_dk3s_zdim_re (- g_dk3s_re_r re))
              (dk3s_p g_dk3s_zdim_re g_dk3s_re_r) 90.0 "%%c<>"
              (dk3s_dimtxt_v g_dk3s_zdim_re (+ g_dk3s_re_r re) 1.0 (strcat "O" (dk3s_num g_dk3s_re_d 0))))
  (dk3s_dim (dk3s_p zre1 (- g_dk3s_re_r re)) (dk3s_p zre2 (- g_dk3s_re_r re)) (dk3s_p 0.0 -3.0) 0.0 "")
  (dk3s_dim (dk3s_p (+ g_dk3s_z_total 4.0) g_dk3s_re_r) (dk3s_p (+ g_dk3s_z_total 4.0) (- g_dk3s_re_r))
            (dk3s_p (+ g_dk3s_z_total 14.0) 0.0) 90.0 "")
)

(defun dk3s_draw_labels_main ( / ya yb yc ye yd yd2 rs rp rc rre e2)
  ;; полки выносок: ряды над датчиком и под ним (между размерными цепями).
  ;; Раскладка подобрана перебором (19.09.2026, plan_labels.py; запас ширины g_dk3s_font_k, зазор 0,5 мм): при ширине надписей
  ;; шрифтом ГОСТ 2.304 тип Б надписи не пересекаются ни с чем, выноски не пересекают друг друга,
  ;; полки, размеры и надписи; линии деталей пересекают только выноски наконечника (изнутри скобы)
  ;; и токоотвода рабочего электрода (под мостиками). Проверка — tools/lispcheck/check_text_fit.py.
  (setq ya 52.0 yb 68.0 yc 84.0 ye 100.0 yd -46.0 yd2 -52.0)
  (setq rs (/ g_dk3s_sleeve_d 2.0) rp (/ g_dk3s_plate_d 2.0) rc (/ g_dk3s_clamp_d 2.0))
  (setq e2 g_dk3s_hex2_e rre (+ g_dk3s_re_r (/ g_dk3s_re_d 2.0)))
  ;; ряд A
  (dk3s_leader (dk3s_p (- g_dk3s_z_sleeve 2.0) (+ g_dk3s_tip_off (/ g_dk3s_tip_d 2.0)))
               (dk3s_p 31.6 ya) 1 "Наконечник (см. А)")
  (dk3s_leader (dk3s_p 240.0 (/ g_dk3s_shell_d 2.0))
               (dk3s_p 240.0 ya) -1 "Узел сальника")
  (dk3s_leader (dk3s_p (+ g_dk3s_z_clamp1 3.8) rc)
               (dk3s_p (+ g_dk3s_z_clamp1 3.8) ya) 1 "Хомут")
  ;; ряд B
  (dk3s_leader (dk3s_p 0.6 9.5)
               (dk3s_p -7.4 yb) 1 "Скоба защитная")
  (dk3s_leader (dk3s_p 130.0 rs)
               (dk3s_p 130.0 yb) 1 "Труба защитная")
  (dk3s_leader (dk3s_p 327.0 (/ g_dk3s_tag_w 2.0))
               (dk3s_p 327.0 yb) 1 "Бирка с серийным номером")
  (dk3s_leader (dk3s_p 605.0 (+ g_dk3s_re_r (/ g_dk3s_conn_pin_d 2.0)))
               (dk3s_p 571.0 yb) 1 "Токоотвод электрода сравнения")
  ;; ряд C
  (dk3s_leader (dk3s_p 262.3 rp)
               (dk3s_p 262.3 yc) -1 "Фланец узла сальника")
  (dk3s_leader (dk3s_p 298.5 (/ e2 2.0))
               (dk3s_p 298.5 yc) 1 "Гайка нажимная")
  (dk3s_leader (dk3s_p 530.0 rre)
               (dk3s_p 520.0 yc) 1 "Электрод сравнения (2 шт.)")
  ;; ряд D
  (dk3s_leader (dk3s_p 466.0 (+ g_dk3s_bridge_r (/ g_dk3s_bridge_d 2.0)))     ; на мостике перед хомутом
               (dk3s_p 466.0 ye) -1 "Мостик электролитический (2 шт.)")
  (dk3s_leader (dk3s_p 488.0 (/ g_dk3s_conn_body_d 2.0))
               (dk3s_p 488.0 ye) 1 "Токоотвод рабочего электрода")
  ;; снизу, второй ряд
  (dk3s_leader (dk3s_p 400.0 (- g_dk3s_se_r (/ g_dk3s_se_d 2.0)))
               (dk3s_p 400.0 yd2) 1 "Токоотвод вспомогательного электрода")
  ;; обозначение выносного элемента А на главном виде
  (dk3s_circle (dk3s_p 9.0 g_dk3s_tip_off) 20.0 g_dk3s_lay_thin)
  (dk3s_text (dk3s_p 28.0 (+ g_dk3s_tip_off 15.0)) (* 1.4 g_dk3s_txt_h g_dk3s_scale_den) "А" 0.0 0 g_dk3s_lay_text)
)

;; Технические требования: строки переносятся по ширине до рамки (продолжение — с отступом под номером),
;; блок ставится так, чтобы последняя строка была на 8 мм выше основной надписи; y — не выше этого уровня
(defun dk3s_draw_notes (x y / h dy lines i xr rows w0 n y0 r)
  (setq h (* g_dk3s_txt_h g_dk3s_scale_den) dy (* h 1.7))
  (setq xr (* g_dk3s_scale_den (- g_dk3s_sheet_w 8.0)))          ; правый край текста: рамка минус 3 мм
  (setq lines (list
    "1. * Размеры для справок."
    "2. Электрод рабочий - платиновая проволока Ø1,4 мм, выступ 2 мм."
    "3. Наконечник и трубка токоотвода - фторопласт. Наконечник накручен на токоотвод (резьба M3x0,5), шестигранник 1/4\"; трубка надета на хвостовик наконечника с натягом."
    "4. Присоединение - резьба M42x3 в гнездо 713.165.001 узла ввода; фланец DN50 и патрубок на аппарате изготавливает заказчик."
    "5. Узел сальника, гайка нажимная, грундбукса - сталь 08Х18Н10Т ГОСТ 5949-75 (черт. 714.761.000, 714.541.000, 711.171.000)."
    "6. Токоотводы: RE1 - синий, RE2 - белый, WE - красный, SE - чёрный."
    "7. Геометрия - по монтажному чертежу техописания K1 (лист 16) и чертежам деталей ЭКОР."
    "8. Сальник 715412.001 - фторопласт Ф-4Д ГОСТ 14906-77; между грундбуксой и гайкой нажимной - шайба пружинная 20 65Г ГОСТ 6402-70 (гровер)."
    "9. Изометрия - приведённая по ГОСТ 2.317, вырезана четверть корпусных деталей; трубки внутри трубы защитной показаны условно."))
  ;; разбивка на строки: список (текст отступ)
  (setq rows nil)
  (foreach s lines
    (setq w0 (- (dk3s_text_w (substr s 1 3) h) (* 0.27 h)))       ; ширина "N. " — отступ продолжения
    (setq r 0)
    (foreach ln (dk3s_wrap s h (- xr x) (- xr x w0))
      (setq rows (cons (list ln (if (= r 0) 0.0 w0)) rows) r (1+ r))
    )
  )
  (setq rows (reverse rows) n (length rows))
  (setq y0 (+ g_dk3s_tby (* g_dk3s_scale_den 63.0) (* (1- n) dy)))  ; низ последней строки: штамп + 8 мм
  (if (< y y0) (setq y0 y))
  (setq i 0)
  (foreach rw rows
    (dk3s_text (dk3s_ps (+ x (cadr rw)) (- y0 (* i dy))) h (car rw) 0.0 0 g_dk3s_lay_text)
    (setq i (1+ i))
  )
)

;;; ---------------------------------------------------------------------------
;;; 10. ГЛАВНАЯ КОМАНДА (конечный автомат стадий: INIT -> TABLES -> FRAME ->
;;;     MAIN -> DIMS -> LABELS -> DETAIL -> ISO -> NOTES -> DONE)
;;; ---------------------------------------------------------------------------

(defun dk3s_error (msg)
  (if (not (member msg '("Function cancelled" "quit / exit abort")))
    (princ (strcat "\nDK3S: error at stage " g_dk3s_stage ": " msg))
  )
  (dk3s_restore)
  (princ)
)

(defun dk3s_restore ()
  (if g_dk3s_old_err (setq *error* g_dk3s_old_err))
  (if g_dk3s_old_vars
    (foreach v g_dk3s_old_vars (setvar (car v) (cdr v)))
  )
  (setq g_dk3s_old_vars nil)
)

(defun c:dk3s ( / s)
  (setq g_dk3s_old_err *error* *error* dk3s_error)
  (setq g_dk3s_stage "INIT" g_dk3s_cnt 0 g_dk3s_dim_mode "entmake")
  (setq g_dk3s_old_vars (list (cons "CMDECHO" (getvar "CMDECHO")) (cons "OSMODE" (getvar "OSMODE"))
                              (cons "CLAYER" (getvar "CLAYER"))))
  (setvar "CMDECHO" 0) (setvar "OSMODE" 0)
  (setq s g_dk3s_scale_den)

  (setq g_dk3s_stage "TABLES")
  (dk3s_make_ltype)
  ;; все слои — цвет 7: чёрный на бумаге и на светлом фоне (на тёмном CAD показывает его белым);
  ;; слово Леонида 26.09.2026 «сделай чёрным и ДК-3С» (v1.3.4; было: тонкие 8, осевые 1, размеры 4, надписи 2)
  (dk3s_make_layer g_dk3s_lay_main  7 "Continuous" g_dk3s_lw_main)
  (dk3s_make_layer g_dk3s_lay_thin  7 "Continuous" g_dk3s_lw_thin)
  (dk3s_make_layer g_dk3s_lay_axis  7 g_dk3s_ltype_axis g_dk3s_lw_thin)
  (dk3s_make_layer g_dk3s_lay_dim   7 "Continuous" g_dk3s_lw_dim)
  (dk3s_make_layer g_dk3s_lay_text  7 "Continuous" g_dk3s_lw_dim)
  (dk3s_make_layer g_dk3s_lay_frame 7 "Continuous" g_dk3s_lw_frame)
  (dk3s_make_layer g_dk3s_lay_iso   7 "Continuous" g_dk3s_lw_iso)
  (dk3s_make_style)
  (dk3s_make_dimstyle)

  (setq g_dk3s_stage "FRAME")
  (dk3s_draw_frame)

  (setq g_dk3s_stage "MAIN")
  (setq g_dk3s_ox (* s g_dk3s_main_x) g_dk3s_oy (* s g_dk3s_main_y) g_dk3s_k 1.0)   ; начало главного вида
  (dk3s_draw_main_view)

  (setq g_dk3s_stage "DIMS")
  (dk3s_draw_dims_main)

  (setq g_dk3s_stage "LABELS")
  (dk3s_draw_labels_main)

  (setq g_dk3s_stage "DETAIL")
  (setq g_dk3s_ox (* s g_dk3s_det_x) g_dk3s_oy (* s g_dk3s_det_y) g_dk3s_k g_dk3s_detail_mul)
  (dk3s_draw_detail_a)

  (setq g_dk3s_stage "ISO")
  (setq g_dk3s_ox 0.0 g_dk3s_oy 0.0 g_dk3s_k 1.0)
  (dk3s_draw_iso)

  (setq g_dk3s_stage "NOTES")
  (dk3s_draw_notes (* s g_dk3s_notes_x) (* s g_dk3s_notes_y))

  (setq g_dk3s_stage "DONE")
  (command "_.ZOOM" "_E")
  (dk3s_restore)
  (princ (strcat "\nDK3S: drawing complete, entities: " (itoa g_dk3s_cnt)
                 ", dims: " g_dk3s_dim_mode ", text style: " g_dk3s_style))
  (princ)
)

;;; === ISO BEGIN (раздел генерируется tools/iso/build_iso_lsp.py) ===
;;; ---------------------------------------------------------------------------
;;; 11. ИЗОМЕТРИЯ С ВЫРЕЗОМ — СГЕНЕРИРОВАНО tools/iso/build_iso_lsp.py из модели FreeCAD
;;;     (tools/iso/sensor_model.py -> sensor_iso_fc.py). Руками не править: менять модель и выноски.
;;; ---------------------------------------------------------------------------
(defun dk3s_draw_iso ()
  (dk3s_iso_pl '(11.8 17.19 11.65 17.24 11.49 17.22))
  (dk3s_iso_pl '(12.11 16.16 12.21 16.29 12.23 16.47 12.2 16.64 12.05 16.95 11.8 17.19))
  (dk3s_iso_pl '(5.05 6.29 4.92 6.58 4.87 6.89))
  (dk3s_iso_pl '(5.91 6.79 6.09 6.89))
  (dk3s_iso_pl '(6.09 6.89 5.91 6.79))
  (dk3s_iso_pl '(5.91 6.79 5.05 6.29))
  (dk3s_iso_pl '(5.05 6.29 4.87 6.19))
  (dk3s_iso_pl '(4.87 6.19 5.05 6.29))
  (dk3s_iso_pl '(5.48 5.83 5.23 6.03 5.05 6.29))
  (dk3s_iso_pl '(6.03 13.99 5.86 13.97))
  (dk3s_iso_pl '(17.43 7.44 17.68 7.2 17.83 6.89 17.86 6.72 17.84 6.54 17.74 6.41))
  (dk3s_iso_pl '(17.12 7.47 17.28 7.49 17.43 7.44))
  (dk3s_iso_pl '(12.21 3.29 12.11 3.16))
  (dk3s_iso_pl '(14.24 14.17 14.57 14.11 14.87 13.96))
  (dk3s_iso_pl '(14.24 14.17 15.51 13.43))
  (dk3s_iso_pl '(14.87 13.96 15.15 13.78 15.51 13.43))
  (dk3s_iso_pl '(11.73 12.72 11.91 12.45 12.17 12.24))
  (dk3s_iso_pl '(12.17 12.24 12.49 12.1 13 11.98))
  (dk3s_iso_pl '(13 11.98 15.51 13.43))
  (dk3s_iso_pl '(11.73 12.72 14.24 14.17))
  (dk3s_iso_pl '(13 11.98 13.23 11.69))
  (dk3s_iso_pl '(13.23 11.69 13.26 11.19 13.38 10.71 13.54 10.42 13.87 10.05))
  (dk3s_iso_pl '(13.87 10.05 13.87 9.74))
  (dk3s_iso_pl '(13.87 9.74 13.53 9.39 13.34 9.13 13.26 8.99 13.23 8.83))
  (dk3s_iso_pl '(13.23 8.83 13 8.81))
  (dk3s_iso_pl '(13 8.81 12.55 8.91))
  (dk3s_iso_pl '(10.86 11.89 11.02 12.19 11.49 12.7))
  (dk3s_iso_pl '(11.49 12.7 11.73 12.72))
  (dk3s_iso_pl '(10.85 10.34 11.08 10.12 11.22 9.83 11.24 9.67 11.21 9.51 11.1 9.4 10.94 9.4))
  (dk3s_iso_pl '(10.94 9.4 10.89 9.42))
  (dk3s_iso_pl '(10.46 10.16 10.47 10.21))
  (dk3s_iso_pl '(10.47 10.21 10.55 10.35 10.7 10.39 10.85 10.34))
  (dk3s_iso_pl '(11.49 12.7 14 14.15))
  (dk3s_iso_pl '(13.63 13.94 13.8 14.07))
  (dk3s_iso_pl '(13.8 14.07 14 14.15))
  (dk3s_iso_pl '(13.23 8.83 15.75 10.28))
  (dk3s_iso_pl '(16.38 11.19 15.75 10.28))
  (dk3s_iso_pl '(13.87 9.74 16.38 11.19))
  (dk3s_iso_pl '(16.38 11.19 16.32 10.87 16.27 10.72 16.08 10.45 15.95 10.36))
  (dk3s_iso_pl '(15.95 10.36 15.75 10.28))
  (dk3s_iso_pl '(13.87 10.05 16.38 11.5))
  (dk3s_iso_pl '(15.75 13.14 16.38 11.5))
  (dk3s_iso_pl '(13.23 11.69 15.75 13.14))
  (dk3s_iso_pl '(15.75 13.14 16 12.73 16.2 12.29 16.34 11.82 16.38 11.5))
  (dk3s_iso_pl '(14.87 13.96 20.29 17.09))
  (dk3s_iso_pl '(20.29 17.09 20.67 16.81 21.1 16.35 21.44 15.81 21.68 15.23 21.8 14.6 21.77 14.13 21.67 13.83 21.59 13.69 21.36 13.48))
  (dk3s_iso_pl '(19.22 17.2 19.36 17.26 19.68 17.29 20 17.22 20.29 17.09))
  (dk3s_iso_pl '(9.98 9.74 10.11 9.63 10.21 9.49 10.27 9.33 10.28 9.16 10.2 9.02))
  (dk3s_iso_pl '(10.2 9.02 10.05 9.01 9.91 9.09 9.73 9.33 9.69 9.48 9.69 9.63 9.77 9.76))
  (dk3s_iso_pl '(9.77 9.76 9.98 9.74))
  (dk3s_iso_pl '(18.73 6.19 18.69 5.41 18.61 4.79 18.43 4.03 18.21 3.45 17.91 2.9 17.54 2.4 17.09 1.97 16.7 1.7))
  (dk3s_iso_pl '(16.7 1.7 16.13 1.44 15.53 1.29 14.91 1.24 14.13 1.31 13.37 1.49 12.64 1.76 11.94 2.11 11.14 2.6))
  (dk3s_iso_pl '(7.88 5.86 7.35 6.63 6.86 7.43 6.42 8.25 6.09 8.95))
  (dk3s_iso_pl '(4.9 13.41 4.87 14.35 4.92 15.13 5.05 15.9 5.27 16.65 5.61 17.35 5.96 17.86 6.39 18.31 6.9 18.67))
  (dk3s_iso_pl '(6.9 18.67 7.32 18.88 7.92 19.06 8.54 19.13 9.16 19.11 9.78 19.01 10.53 18.79 11.11 18.55 11.8 18.19))
  (dk3s_iso_pl '(18.73 6.19 21.72 7.91))
  (dk3s_iso_pl '(21.72 7.91 21.75 7.55 21.81 7.38 21.9 7.23 22.04 7.11))
  (dk3s_iso_pl '(22.04 7.11 22.21 7.05 22.39 7.05 22.56 7.09 22.89 7.24))
  (dk3s_iso_pl '(22.89 7.24 23.4 7.62 23.72 7.97 23.91 8.23 24.2 8.79 24.28 9.1 24.31 9.41))
  (dk3s_iso_pl '(24.31 9.41 30.38 12.91))
  (dk3s_iso_pl '(30.38 12.91 30.41 12.55 30.47 12.38 30.56 12.23 30.7 12.11))
  (dk3s_iso_pl '(30.7 12.11 30.87 12.05 31.05 12.05 31.22 12.09 31.55 12.24))
  (dk3s_iso_pl '(31.55 12.24 32.06 12.62 32.38 12.97 32.57 13.23 32.86 13.79 32.94 14.1 32.97 14.41))
  (dk3s_iso_pl '(32.97 14.41 39.04 17.91))
  (dk3s_iso_pl '(39.04 17.91 39.07 17.55 39.13 17.38 39.22 17.23 39.36 17.11))
  (dk3s_iso_pl '(39.36 17.11 39.53 17.05 39.71 17.05 39.88 17.09 40.21 17.24))
  (dk3s_iso_pl '(40.21 17.24 40.72 17.62 41.04 17.97 41.23 18.23 41.52 18.79 41.6 19.1 41.63 19.41))
  (dk3s_iso_pl '(41.63 19.41 112.04 60.06))
  (dk3s_iso_pl '(112.04 60.06 112.04 60.01))
  (dk3s_iso_pl '(105.07 72.09 105.11 72.06))
  (dk3s_iso_pl '(30.38 28.91 105.11 72.06))
  (dk3s_iso_pl '(30.38 28.91 30.09 29.04 29.78 29.12 29.14 29.16 28.83 29.13 28.36 29.02 27.78 28.77))
  (dk3s_iso_pl '(27.78 28.77 27.49 28.56 27.36 28.43 27.27 28.27 27.24 28.09))
  (dk3s_iso_pl '(27.24 28.09 27.27 27.92 27.36 27.76 27.49 27.63 27.78 27.41))
  (dk3s_iso_pl '(21.72 23.91 27.78 27.41))
  (dk3s_iso_pl '(21.72 23.91 21.43 24.04 21.12 24.12 20.48 24.16 20.17 24.13 19.7 24.02 19.12 23.77))
  (dk3s_iso_pl '(19.12 23.77 18.82 23.56 18.7 23.43 18.61 23.27 18.58 23.09))
  (dk3s_iso_pl '(18.58 23.09 18.61 22.92 18.7 22.76 18.82 22.63 19.12 22.41))
  (dk3s_iso_pl '(11.8 18.19 19.12 22.41))
  (dk3s_iso_pl '(18.75 7.74 18.85 7.85 19.1 8.04 19.53 8.22 19.99 8.3 20.61 8.27))
  (dk3s_iso_pl '(21.72 7.91 21.96 7.74))
  (dk3s_iso_pl '(27.41 12.74 27.51 12.85 27.76 13.04 28.19 13.22 28.65 13.3 29.27 13.27))
  (dk3s_iso_pl '(30.38 12.91 30.62 12.74))
  (dk3s_iso_pl '(17.86 6.69 18.73 6.19))
  (dk3s_iso_pl '(17.86 6.69 17.84 6.07 17.76 5.45 17.61 4.85 17.39 4.26 17.09 3.72 16.81 3.35 16.47 3.03 16.09 2.76))
  (dk3s_iso_pl '(16.09 2.76 15.67 2.57 15.23 2.44 14.77 2.37 14.16 2.38 13.7 2.44 13.11 2.6 12.53 2.82 11.98 3.09))
  (dk3s_iso_pl '(9.76 4.77 9.13 5.45 8.54 6.17 8 6.93 7.51 7.71 7.07 8.53 6.69 9.38 6.36 10.24 6.09 11.13))
  (dk3s_iso_pl '(5.74 13.9 5.78 14.51 5.88 15.12 6.04 15.71 6.22 16.14 6.52 16.67 6.8 17.03 7.13 17.35 7.51 17.61))
  (dk3s_iso_pl '(7.51 17.61 7.93 17.81 8.38 17.94 8.84 18.01 9.47 18 10.08 17.89 10.68 17.72 11.25 17.48 11.8 17.19))
  (dk3s_iso_pl '(11.8 17.19 11.8 18.19))
  (dk3s_iso_pl '(17.86 6.69 20.85 8.41))
  (dk3s_iso_pl '(20.85 8.41 21.72 7.91))
  (dk3s_iso_pl '(21.74 7.62 22.01 7.75))
  (dk3s_iso_pl '(23.45 9.91 24.31 9.41))
  (dk3s_iso_pl '(22.01 7.75 22.52 8.13 22.84 8.47 23.03 8.73 23.33 9.29 23.42 9.6 23.45 9.91))
  (dk3s_iso_pl '(23.45 9.91 29.51 13.41))
  (dk3s_iso_pl '(29.51 13.41 30.38 12.91))
  (dk3s_iso_pl '(30.4 12.62 30.67 12.75))
  (dk3s_iso_pl '(32.11 14.91 32.97 14.41))
  (dk3s_iso_pl '(30.67 12.75 31.18 13.13 31.51 13.47 31.7 13.73 31.99 14.29 32.08 14.6 32.11 14.91))
  (dk3s_iso_pl '(32.11 14.91 38.17 18.41))
  (dk3s_iso_pl '(38.17 18.41 39.04 17.91))
  (dk3s_iso_pl '(39.06 17.62 39.33 17.75))
  (dk3s_iso_pl '(40.77 19.91 41.63 19.41))
  (dk3s_iso_pl '(39.33 17.75 39.84 18.13 40.17 18.47 40.36 18.73 40.65 19.29 40.74 19.6 40.77 19.91))
  (dk3s_iso_pl '(40.77 19.91 111.18 60.56))
  (dk3s_iso_pl '(111.18 60.56 112.04 60.06))
  (dk3s_iso_pl '(105.11 71.06 105.11 72.06))
  (dk3s_iso_pl '(30.38 27.91 30.38 28.91))
  (dk3s_iso_pl '(30.38 27.91 105.11 71.06))
  (dk3s_iso_pl '(30.38 27.91 30.09 28.04 29.78 28.12 29.14 28.15 28.83 28.11 28.36 28 27.78 27.75))
  (dk3s_iso_pl '(27.78 26.41 27.78 27.41))
  (dk3s_iso_pl '(27.78 27.75 27.53 27.58))
  (dk3s_iso_pl '(21.72 22.91 21.72 23.91))
  (dk3s_iso_pl '(21.72 22.91 27.78 26.41))
  (dk3s_iso_pl '(21.72 22.91 21.43 23.04 21.12 23.12 20.48 23.15 20.17 23.11 19.7 23 19.12 22.75))
  (dk3s_iso_pl '(19.12 21.41 19.12 22.41))
  (dk3s_iso_pl '(19.12 22.75 18.87 22.58))
  (dk3s_iso_pl '(11.8 17.19 19.12 21.41))
  (dk3s_iso_pl '(19.12 7.41 18.85 7.62 18.74 7.76 18.6 8.07 18.58 8.24))
  (dk3s_iso_pl '(18.58 8.24 18.59 8.4 18.71 8.69 18.8 8.81 19.03 9.02 19.3 9.16 19.59 9.26 20.21 9.32 20.51 9.3 20.97 9.21 21.41 9.06 21.69 8.93 22.06 8.65 22.23 8.4 22.25 8.24))
  (dk3s_iso_pl '(22.25 8.24 22.22 8.07 22.13 7.91 21.86 7.67))
  (dk3s_iso_pl '(27.78 12.41 27.51 12.62 27.4 12.76 27.26 13.07 27.24 13.24))
  (dk3s_iso_pl '(27.24 13.24 27.25 13.4 27.37 13.69 27.46 13.81 27.69 14.02 27.96 14.16 28.25 14.26 28.87 14.32 29.17 14.3 29.63 14.21 30.07 14.06 30.35 13.93 30.72 13.65 30.89 13.4 30.91 13.24))
  (dk3s_iso_pl '(30.91 13.24 30.88 13.07 30.79 12.91 30.52 12.67))
  (dk3s_iso_pl '(102.39 72.49 102.39 70.54))
  (dk3s_iso_pl '(109.36 58.46 109.32 57.68 109.21 56.9 109.06 56.29 108.83 55.7 108.54 55.15 108.16 54.65 107.71 54.21 107.32 53.95))
  (dk3s_iso_pl '(107.32 53.95 106.74 53.69))
  (dk3s_iso_pl '(96.94 70.66 97.46 71.03))
  (dk3s_iso_pl '(97.46 71.03 97.88 71.23 98.48 71.41 99.11 71.49 99.73 71.47 100.35 71.36 101.11 71.14 101.69 70.9 102.39 70.54))
  (dk3s_iso_pl '(111.05 57.49 109.36 58.46))
  (dk3s_iso_pl '(111.05 57.49 111.01 56.57 110.91 55.81 110.75 55.06 110.51 54.33 110.18 53.63 109.85 53.11 109.36 52.53 108.89 52.13 108.37 51.8 107.81 51.56 107.21 51.4 106.45 51.31 105.84 51.32 105.08 51.43 104.33 51.62 103.61 51.88))
  (dk3s_iso_pl '(93.81 68.85 93.95 69.61 94.15 70.35 94.44 71.06 94.74 71.6 95.2 72.21 95.63 72.65 96.12 73.01 96.67 73.3 97.25 73.5 98 73.64 98.61 73.67 99.38 73.6 100.13 73.45 100.86 73.21 101.57 72.92 102.39 72.49))
  (dk3s_iso_pl '(102.39 70.54 105.11 72.11))
  (dk3s_iso_pl '(105.11 69.26 105.11 72.11))
  (dk3s_iso_pl '(105.11 69.26 106.07 69.81))
  (dk3s_iso_pl '(106.07 69.81 107.22 72.78))
  (dk3s_iso_pl '(107.22 72.78 118.19 79.11))
  (dk3s_iso_pl '(118.19 80.11 118.19 79.11))
  (dk3s_iso_pl '(118.19 80.11 120.14 81.24))
  (dk3s_iso_pl '(120.14 81.01 120.14 81.24))
  (dk3s_iso_pl '(120.14 81.01 128.8 86.01))
  (dk3s_iso_pl '(128.8 86.01 128.8 89.24))
  (dk3s_iso_pl '(128.05 90.31 128.8 89.24))
  (dk3s_iso_pl '(120.14 85.74 128.05 90.31))
  (dk3s_iso_pl '(120.14 85.74 120.14 87.49))
  (dk3s_iso_pl '(117.11 85.74 120.14 87.49))
  (dk3s_iso_pl '(117.11 85.74 117.11 80.74))
  (dk3s_iso_pl '(114.94 79.49 117.11 80.74))
  (dk3s_iso_pl '(114.94 79.49 114.94 80.24))
  (dk3s_iso_pl '(102.82 73.24 114.94 80.24))
  (dk3s_iso_pl '(102.39 72.49 102.82 73.24))
  (dk3s_iso_pl '(109.36 58.46 112.09 60.04))
  (dk3s_iso_pl '(109.62 61.46 112.09 60.04))
  (dk3s_iso_pl '(109.62 61.46 110.57 62.01))
  (dk3s_iso_pl '(110.57 62.01 113.71 61.53))
  (dk3s_iso_pl '(113.71 61.53 124.69 67.86))
  (dk3s_iso_pl '(125.55 67.36 124.69 67.86))
  (dk3s_iso_pl '(125.55 67.36 127.5 68.49))
  (dk3s_iso_pl '(127.31 68.6 127.5 68.49))
  (dk3s_iso_pl '(127.31 68.6 135.97 73.6))
  (dk3s_iso_pl '(135.97 73.6 138.55 72.11))
  (dk3s_iso_pl '(129.89 67.11 138.55 72.11))
  (dk3s_iso_pl '(129.89 67.11 132.91 65.36))
  (dk3s_iso_pl '(129.88 63.61 132.91 65.36))
  (dk3s_iso_pl '(129.88 63.61 125.55 66.11))
  (dk3s_iso_pl '(123.39 64.86 125.55 66.11))
  (dk3s_iso_pl '(123.39 64.86 124.04 64.49))
  (dk3s_iso_pl '(111.91 57.49 124.04 64.49))
  (dk3s_iso_pl '(111.05 57.49 111.91 57.49))
  (dk3s_iso_pl '(111.91 57.49 111.86 56.41 111.73 55.5 111.5 54.61 111.23 53.89 110.87 53.21 110.42 52.59 109.88 52.04 109.25 51.6))
  (dk3s_iso_pl '(109.25 51.6 108.69 51.33 108.09 51.14 107.48 51.03 106.7 51 105.92 51.08 105.16 51.24 104.42 51.48 103.55 51.85))
  (dk3s_iso_pl '(93.76 68.82 93.87 69.75 94.03 70.51 94.27 71.26 94.59 71.97 95.01 72.63 95.41 73.11 95.87 73.53 96.39 73.88))
  (dk3s_iso_pl '(96.39 73.88 97.09 74.2 97.83 74.4 98.59 74.48 99.36 74.45 100.12 74.32 101.01 74.07 101.86 73.73 102.82 73.24))
  (dk3s_iso_pl '(109.62 61.46 109.58 60.85 109.51 60.39 109.33 59.79 109.12 59.38))
  (dk3s_iso_pl '(103.06 69.88 103.52 69.85 104.13 69.71 104.56 69.54 105.11 69.26))
  (dk3s_iso_pl '(127.31 68.6 127.3 68.37))
  (dk3s_iso_pl '(119.94 81.13 120.14 81.01))
  (dk3s_iso_pl '(122.17 90.15 125.68 90.46))
  (dk3s_iso_pl '(138.55 72.11 138.55 69.76))
  (dk3s_iso_pl '(128.05 90.31 126.95 90.43 125.68 90.46))
  (dk3s_iso_pl '(122.17 90.15 120.31 89.83 118.3 89.44))
  (dk3s_iso_pl '(117.19 88.79 118.3 89.44))
  (dk3s_iso_pl '(132.91 65.36 132.86 63.99 132.67 62.62 132.37 61.43 131.94 60.28 131.44 59.33 130.81 58.47 130.39 58.02 130.05 57.71 129.56 57.34 129.17 57.09))
  (dk3s_iso_pl '(111.11 88.38 111.51 88.6 112.08 88.84 112.52 88.98 113.11 89.11 114.18 89.23 115.25 89.19 116.46 88.99 117.64 88.65 118.92 88.13 120.14 87.49))
  (dk3s_iso_pl '(129.88 63.61 129.82 62.24 129.64 60.87 129.34 59.68 128.91 58.53 128.41 57.58 127.78 56.72 127.36 56.27 127.02 55.96 126.53 55.59 126.14 55.34))
  (dk3s_iso_pl '(126.14 55.34 125.73 55.13 125.16 54.89 124.72 54.75 124.12 54.61 123.05 54.5 121.97 54.54 120.76 54.75 119.57 55.09 118.43 55.56 117.2 56.19))
  (dk3s_iso_pl '(104.34 78.46 104.4 79.85 104.57 81.07 104.87 82.27 105.3 83.42 105.8 84.38 106.43 85.25 106.85 85.7 107.19 86.01 107.69 86.39 108.08 86.63))
  (dk3s_iso_pl '(108.08 86.63 108.48 86.85 109.05 87.09 109.49 87.23 110.08 87.36 111.15 87.48 112.22 87.44 113.43 87.24 114.61 86.9 115.89 86.38 117.11 85.74))
  (dk3s_iso_pl '(125.55 66.11 125.51 65.19 125.41 64.43 125.24 63.67 124.99 62.94 124.65 62.25 124.31 61.74 123.79 61.17 123.31 60.79))
  (dk3s_iso_pl '(111.38 81.46 111.95 81.69 112.7 81.85 113.32 81.89 114.08 81.84 114.84 81.69 115.58 81.46 116.29 81.17 117.11 80.74))
  (dk3s_iso_pl '(124.04 64.49 123.99 63.41 123.85 62.5 123.63 61.61 123.35 60.89 122.99 60.21 122.54 59.59 122 59.04 121.37 58.6))
  (dk3s_iso_pl '(108.51 80.88 109.21 81.2 109.95 81.4 110.72 81.48 111.48 81.45 112.24 81.32 113.13 81.07 113.99 80.73 114.94 80.24))
  (dk3s_iso_pl '(132.57 62.16 137.8 65.18))
  (dk3s_iso_pl '(137.8 65.18 138.27 67.61 138.55 69.76))
  (dk3s_iso_pl '(132.85 92.75 135.08 92.95))
  (dk3s_iso_pl '(145.49 78.5 145.49 77.02))
  (dk3s_iso_pl '(142.33 80.33 145.49 78.5))
  (dk3s_iso_pl '(137.81 88.16 137.81 91.94))
  (dk3s_iso_pl '(137.18 92.83 136.21 92.93 135.08 92.95))
  (dk3s_iso_pl '(137.18 92.83 137.81 91.94))
  (dk3s_iso_pl '(128.12 90.21 133.48 90.69))
  (dk3s_iso_pl '(133.48 90.69 137.18 92.83))
  (dk3s_iso_pl '(132.85 92.75 131.32 92.5 129.49 92.14))
  (dk3s_iso_pl '(126.56 90.45 129.49 92.14))
  (dk3s_iso_pl '(141.16 70.88 138.55 70.64))
  (dk3s_iso_pl '(141.16 70.88 144.87 73.01))
  (dk3s_iso_pl '(144.87 73.01 145.27 75.16 145.49 77.02))
  (dk3s_iso_pl '(141.16 76 141.16 70.88))
  (dk3s_iso_pl '(141.16 76 145.49 78.5))
  (dk3s_iso_pl '(139.97 76.69 141.16 76))
  (dk3s_iso_pl '(138.5 75.84 139.97 76.69))
  (dk3s_iso_pl '(138.5 75.84 139.15 75.46))
  (dk3s_iso_pl '(131.96 71.31 139.15 75.46))
  (dk3s_iso_pl '(131.96 71.31 129.34 72.83))
  (dk3s_iso_pl '(142.33 80.33 129.34 72.83))
  (dk3s_iso_pl '(137.81 88.16 124.82 80.66))
  (dk3s_iso_pl '(133.48 87.94 133.48 90.69))
  (dk3s_iso_pl '(132 87.09 133.48 87.94))
  (dk3s_iso_pl '(132 87.09 132 87.84))
  (dk3s_iso_pl '(124.82 83.69 132 87.84))
  (dk3s_iso_pl '(124.82 83.69 124.82 80.66))
  (dk3s_iso_pl '(139.97 76.69 139.9 75.59 139.78 74.97 139.64 74.52 139.47 74.08 139.25 73.67 138.98 73.28 138.77 73.04))
  (dk3s_iso_pl '(129.72 88.73 130.03 88.79 130.5 88.82 130.97 88.81 131.43 88.74 131.89 88.63 132.49 88.42 133.48 87.94))
  (dk3s_iso_pl '(139.15 75.46 139.1 74.54 138.95 73.63 138.72 72.9 138.39 72.2))
  (dk3s_iso_pl '(128.8 88.81 129.57 88.75 130.32 88.58 131.18 88.26 132 87.84))
  (dk3s_iso_pl '(131.96 71.31 131.96 71.29))
  (dk3s_iso_pl '(124.79 83.7 124.82 83.69))
  (dk3s_iso_pl '(122.87 81.69 124.82 82.81))
  (dk3s_iso_pl '(122.03 82.11 122.87 81.69))
  (dk3s_iso_pl '(123.98 83.23 124.82 82.81))
  (dk3s_iso_pl '(122.87 79.49 122.87 81.69))
  (dk3s_iso_pl '(122.87 79.49 124.82 80.61))
  (dk3s_iso_pl '(124.82 80.61 124.82 82.81))
  (dk3s_iso_pl '(122.85 79.5 122.87 79.49))
  (dk3s_iso_pl '(131.2 71.75 131.15 70.82))
  (dk3s_iso_pl '(129.25 70.63 129.2 69.69))
  (dk3s_iso_pl '(129.25 70.63 131.2 71.75))
  (dk3s_iso_pl '(129.3 72.85 131.2 71.75))
  (dk3s_iso_pl '(127.35 71.73 129.25 70.63))
  (dk3s_iso_pl '(127.35 71.73 127.35 71.7))
  (dk3s_iso_pl '(127.35 71.73 129.3 72.85))
  (dk3s_iso_pl '(125.36 68.38 124.37 68.94))
  (dk3s_iso_pl '(125.36 68.38 125.31 67.5))
  (dk3s_iso_pl '(118.19 79.83 118.97 79.44))
  (dk3s_iso_pl '(118.97 79.44 118.97 78.3))
  (dk3s_iso_pl '(123.99 69.76 123.96 69.18))
  (dk3s_iso_pl '(118.97 77.83 119.49 77.56))
  (dk3s_iso_pl '(123.99 69.76 124.37 68.94))
  (dk3s_iso_pl '(119.49 77.56 118.97 78.3))
  (dk3s_iso_pl '(127.37 71.71 123.99 69.76))
  (dk3s_iso_pl '(127.37 71.71 129.25 70.63))
  (dk3s_iso_pl '(125.36 68.38 129.25 70.63))
  (dk3s_iso_pl '(129.25 70.63 129.2 69.69))
  (dk3s_iso_pl '(122.03 82.11 122.87 81.69))
  (dk3s_iso_pl '(118.97 79.44 122.87 81.69))
  (dk3s_iso_pl '(122.87 79.51 119.49 77.56))
  (dk3s_iso_pl '(122.87 79.51 122.87 81.69))
  (dk3s_iso_pl '(100.57 66.56 100.57 64.48))
  (dk3s_iso_pl '(99.38 66.03 99.75 65.76 100.06 65.42 100.39 64.9 100.57 64.48))
  (dk3s_iso_pl '(100.57 63.16 100.46 63.01 100.31 62.89))
  (dk3s_iso_pl '(100.31 62.89 100.13 62.82))
  (dk3s_iso_pl '(98.29 66 98.44 66.13))
  (dk3s_iso_pl '(98.44 66.13 98.59 66.19 98.92 66.2 99.08 66.17 99.38 66.03))
  (dk3s_iso_pl '(100.57 63.16 100.57 61.44))
  (dk3s_iso_pl '(101.08 61.14 100.57 61.44))
  (dk3s_iso_pl '(104.27 59.3 104.24 58.98 104.19 58.82 104.01 58.55 103.88 58.45))
  (dk3s_iso_pl '(103.88 58.45 103.68 58.37))
  (dk3s_iso_pl '(105.01 58.88 104.27 59.3))
  (dk3s_iso_pl '(105.01 58.88 104.97 58.26 104.86 57.65 104.65 57.06 104.41 56.66))
  (dk3s_iso_pl '(102.79 55.72 102.15 55.74 101.53 55.88 100.94 56.12 100.25 56.51))
  (dk3s_iso_pl '(96.98 60.48 96.8 60.9))
  (dk3s_iso_pl '(96.19 64.79 96.37 65.53 96.56 65.96 96.72 66.22))
  (dk3s_iso_pl '(98.35 67.16 98.82 67.16 99.43 67.05 100.01 66.84 100.57 66.56))
  (dk3s_iso_pl '(99.38 61.27 99.77 60.98 100.1 60.61))
  (dk3s_iso_pl '(98.29 61.24 98.44 61.36))
  (dk3s_iso_pl '(98.44 61.36 98.59 61.43 98.92 61.44 99.08 61.4 99.38 61.27))
  (dk3s_iso_pl '(100.57 64.48 141.7 88.23))
  (dk3s_iso_pl '(141.7 88.23 141.7 89.89))
  (dk3s_iso_pl '(141.27 89.64 141.7 89.89))
  (dk3s_iso_pl '(141.27 89.64 141.27 90.14))
  (dk3s_iso_pl '(137.81 88.14 141.27 90.14))
  (dk3s_iso_pl '(137.81 88.14 137.81 88.06))
  (dk3s_iso_pl '(118.97 77.19 137.81 88.06))
  (dk3s_iso_pl '(118.97 77.19 118.97 79.31))
  (dk3s_iso_pl '(107.09 72.46 118.97 79.31))
  (dk3s_iso_pl '(106.03 69.72 107.09 72.46))
  (dk3s_iso_pl '(100.57 66.56 106.03 69.72))
  (dk3s_iso_pl '(100.57 63.16 141.7 86.91))
  (dk3s_iso_pl '(100.57 61.44 141.7 85.19))
  (dk3s_iso_pl '(141.7 85.19 141.7 86.91))
  (dk3s_iso_pl '(141.7 85.19 142.25 84.87))
  (dk3s_iso_pl '(104.27 59.3 145.41 83.05))
  (dk3s_iso_pl '(145.41 83.05 145.77 82.84))
  (dk3s_iso_pl '(145.34 82.59 145.77 82.84))
  (dk3s_iso_pl '(145.34 82.59 145.77 82.34))
  (dk3s_iso_pl '(142.31 80.34 145.77 82.34))
  (dk3s_iso_pl '(142.31 80.34 142.25 80.38))
  (dk3s_iso_pl '(123.41 69.5 142.25 80.38))
  (dk3s_iso_pl '(123.41 69.5 125.25 68.44))
  (dk3s_iso_pl '(113.37 61.58 125.25 68.44))
  (dk3s_iso_pl '(110.47 62.03 113.37 61.58))
  (dk3s_iso_pl '(105.01 58.88 110.47 62.03))
  (dk3s_iso_pl '(110.47 62.03 110.47 61.95))
  (dk3s_iso_pl '(105.96 69.75 106.03 69.72))
  (dk3s_iso_pl '(145.77 82.84 145.75 82.35))
  (dk3s_iso_pl '(141.27 90.11 141.7 89.89))
  (dk3s_iso_pl '(145.77 82.34 145.75 81.86 145.69 81.39 145.57 80.92 145.4 80.48 145.16 80.07 144.95 79.82 144.72 79.6 144.46 79.42))
  (dk3s_iso_pl '(138.09 90.45 138.37 90.59 138.68 90.69 138.99 90.74 139.47 90.74 139.94 90.67 140.4 90.54 140.85 90.36 141.27 90.14))
  (dk3s_iso_pl '(142.31 80.34 142.31 80.31))
  (dk3s_iso_pl '(137.79 88.15 137.81 88.14))
  (dk3s_iso_pl '(142.25 80.38 142.24 80.28))
  (dk3s_iso_pl '(137.72 88.11 137.81 88.06))
  (dk3s_iso_pl '(125.25 68.44 125.2 67.57))
  (dk3s_iso_pl '(118.19 79.71 118.97 79.31))
  (dk3s_iso_pl '(104.24 59.45 104.23 59.13 104.14 58.81 103.96 58.54 103.82 58.45))
  (dk3s_iso_pl '(102.05 61.66 102.06 61.67))
  (dk3s_iso_pl '(102.06 61.67 102.21 61.73 102.52 61.74 102.68 61.7 102.97 61.57))
  (dk3s_iso_pl '(102.97 61.57 102.97 61.57))
  (dk3s_iso_pl '(102.97 61.57 103.23 61.39 103.46 61.17 103.85 60.66 104.11 60.08 104.2 59.77 104.24 59.45))
  (dk3s_iso_pl '(104.24 59.45 104.24 59.14 104.16 58.83 103.99 58.57 103.87 58.47))
  (dk3s_iso_pl '(103.87 58.47 103.85 58.46))
  (dk3s_iso_pl '(144.09 85.31 144.35 85.13 144.58 84.91 144.79 84.67 145.05 84.26 145.29 83.67 145.36 83.36 145.38 83.04))
  (dk3s_iso_pl '(142.97 85.28 143.08 85.35))
  (dk3s_iso_pl '(143.08 85.35 143.24 85.42 143.58 85.46 143.76 85.43 144.09 85.31))
  (dk3s_iso_pl '(144.09 85.31 144.37 85.18 144.75 84.9 144.98 84.68 145.27 84.3 145.48 83.88 145.57 83.58 145.61 83.26 145.58 82.95))
  (dk3s_iso_pl '(146.24 88.08 146.51 88.23 146.82 88.29 147.13 88.27 147.44 88.18))
  (dk3s_iso_pl '(146.4 88.18 146.52 88.27))
  (dk3s_iso_pl '(146.52 88.27 146.67 88.33 146.99 88.35 147.14 88.31 147.44 88.18))
  (dk3s_iso_pl '(216.07 127.8 216.45 127.52 216.77 127.16 217.1 126.62 217.27 126.17 217.36 125.7 217.33 125.23 217.21 124.93 216.99 124.71))
  (dk3s_iso_pl '(215.15 127.9 215.3 127.96 215.62 127.97 215.77 127.94 216.07 127.8))
  (dk3s_iso_pl '(167.25 103.34 167.64 103.09 168.11 102.69 168.44 102.37 168.83 101.89 169.18 101.39 169.49 100.86 169.75 100.3 169.96 99.72 170.11 99.12 170.17 98.66 170.19 98.05 170.14 97.59 170.01 97.15 169.87 96.87 169.58 96.51 169.33 96.33))
  (dk3s_iso_pl '(165.17 103.55 165.61 103.71 166.07 103.74 166.38 103.69 166.68 103.6 167.25 103.34))
  (dk3s_iso_pl '(163.96 101.44 164.35 101.19 164.82 100.79 165.15 100.47 165.54 99.99 165.89 99.49 166.2 98.96 166.46 98.4 166.67 97.82 166.82 97.22 166.88 96.76 166.9 96.15 166.85 95.69 166.72 95.25 166.58 94.97 166.29 94.61 166.04 94.43))
  (dk3s_iso_pl '(166.04 94.43 165.75 94.3 165.27 94.24 164.94 94.27 164.47 94.4))
  (dk3s_iso_pl '(161.37 101.15 161.59 101.43 161.88 101.65))
  (dk3s_iso_pl '(161.88 101.65 162.32 101.81 162.78 101.84 163.09 101.79 163.39 101.7 163.96 101.44))
  (dk3s_iso_pl '(210.64 128.39 211.03 128.14 211.5 127.74 211.83 127.42 212.22 126.94 212.57 126.44 212.88 125.91 213.14 125.35 213.35 124.77 213.49 124.17 213.56 123.71 213.58 123.1 213.52 122.64 213.39 122.2 213.26 121.92 212.97 121.56 212.72 121.38))
  (dk3s_iso_pl '(208.56 128.6 209 128.76 209.46 128.79 209.77 128.74 210.07 128.65 210.64 128.39))
  (dk3s_iso_pl '(207.35 126.49 207.74 126.24 208.21 125.84 208.53 125.52 208.93 125.04 209.28 124.54 209.59 124.01 209.85 123.45 210.05 122.87 210.2 122.27 210.27 121.81 210.29 121.2 210.23 120.74 210.1 120.3 209.97 120.02 209.68 119.66 209.43 119.48))
  (dk3s_iso_pl '(209.43 119.48 209.13 119.35 208.65 119.29 208.33 119.32 207.86 119.45))
  (dk3s_iso_pl '(204.76 126.2 204.98 126.48 205.27 126.7))
  (dk3s_iso_pl '(205.27 126.7 205.7 126.86 206.17 126.89 206.48 126.84 206.78 126.75 207.35 126.49))
  (dk3s_iso_pl '(150.15 94.06 150.66 93.72 151.14 93.32 151.58 92.88 152.07 92.28 152.5 91.64 152.81 91.1 153.13 90.39 153.33 89.8 153.52 89.05 153.6 88.44 153.6 87.81 153.55 87.35 153.43 86.9 153.24 86.48 152.96 86.11 152.6 85.82))
  (dk3s_iso_pl '(147.7 94.31 148.15 94.48 148.46 94.53 148.79 94.53 149.42 94.4 149.72 94.28 150.15 94.06))
  (dk3s_iso_pl '(145.86 91.59 146.38 91.25 146.85 90.85 147.29 90.41 147.78 89.81 148.13 89.3 148.52 88.62 148.84 87.91 149.04 87.33 149.23 86.58 149.31 85.96 149.32 85.34 149.26 84.88 149.15 84.43 148.96 84 148.68 83.63 148.31 83.35))
  (dk3s_iso_pl '(148.31 83.35 147.88 83.17 147.42 83.12 146.95 83.16 146.36 83.34))
  (dk3s_iso_pl '(142.59 90.79 142.73 91.1 142.91 91.39 143.14 91.63 143.41 91.83))
  (dk3s_iso_pl '(143.41 91.83 143.86 92.01 144.18 92.06 144.5 92.05 145.13 91.92 145.43 91.81 145.86 91.59))
  (dk3s_iso_pl '(216.93 128.8 217.44 128.43 217.86 127.96 218.28 127.29 218.52 126.71 218.65 126.09 218.67 125.78 218.64 125.46 218.49 125.02 218.29 124.77 218.16 124.68))
  (dk3s_iso_pl '(215.71 128.93 216.01 129.03 216.33 129.03 216.64 128.94 216.93 128.8))
  (dk3s_iso_pl '(216.07 128.3 216.57 127.93 216.99 127.46 217.41 126.79 217.65 126.21 217.78 125.59 217.8 125.28 217.77 124.96 217.62 124.52 217.42 124.27 217.29 124.18))
  (dk3s_iso_pl '(217.29 124.18 217.14 124.12 216.81 124.07 216.49 124.12 216.18 124.25))
  (dk3s_iso_pl '(214.34 127.43 214.45 127.94))
  (dk3s_iso_pl '(214.84 128.43 215.15 128.53 215.47 128.53 215.78 128.44 216.07 128.3))
  (dk3s_iso_pl '(223 131.93 223.38 131.65 223.8 131.17 224.12 130.63 224.29 130.18 224.39 129.72 224.39 129.24 224.3 128.94 224.22 128.8 223.99 128.58))
  (dk3s_iso_pl '(222 132.03 222.16 132.1 222.51 132.11 222.68 132.07 223 131.93))
  (dk3s_iso_pl '(229.49 134.68 229.73 134.48 229.91 134.22 230.01 133.92 230.02 133.61))
  (dk3s_iso_pl '(230.02 133.61 229.87 133.39))
  (dk3s_iso_pl '(229.11 134.72 229.37 134.73))
  (dk3s_iso_pl '(229.37 134.73 229.49 134.68))
  (dk3s_iso_pl '(229.92 134.55 230.05 134.44 230.12 134.29 230.14 134.13))
  (dk3s_iso_pl '(229.88 134.58 229.92 134.55))
  (dk3s_iso_pl '(21.17 20.86 21.44 20.68 21.67 20.46 21.87 20.22 22.13 19.82 22.38 19.24 22.45 18.93 22.47 18.61))
  (dk3s_iso_pl '(21.13 17.88 20.76 18.18 20.45 18.53 20.13 19.07 19.96 19.51 19.88 19.97 19.91 20.44 20.03 20.73 20.26 20.95))
  (dk3s_iso_pl '(20.26 20.95 20.4 21.01 20.72 21.03 20.88 20.99 21.17 20.86))
  (dk3s_iso_pl '(141.68 88.21 141.75 87.74 141.75 87.42 141.68 87.11 141.55 86.82))
  (dk3s_iso_pl '(146.2 89.72 146.26 89.07 146.2 88.58 146.08 88.28 145.99 88.14 145.75 87.92 145.6 87.86))
  (dk3s_iso_pl '(146.2 89.72 146.35 89.13 146.36 88.67 146.28 88.37 146.21 88.24 145.99 88.03))
  (dk3s_iso_pl '(145.99 88.03 145.8 87.96))
  (dk3s_iso_pl '(231.08 146.98 231.2 147.07 231.37 147.33 231.46 147.78 231.44 148.09 231.38 148.39 231.28 148.68 231.08 149.1 230.82 149.48 230.61 149.71 230.38 149.92 230.13 150.09 229.69 150.24 229.38 150.22 229.24 150.16))
  (dk3s_iso_pl '(22.4 14.39 22.47 13.89 22.45 13.56 22.33 13.24 22.23 13.11 22.09 13))
  (dk3s_iso_pl '(22.09 13 21.8 12.92 21.49 12.96 21.21 13.08 20.95 13.25))
  (dk3s_iso_pl '(145.03 87.69 145.38 87.34))
  (dk3s_iso_pl '(145.34 87.78 145.6 87.53))
  (dk3s_iso_pl '(231.08 124.18 231.2 124.27 231.37 124.53 231.46 124.98 231.44 125.29 231.38 125.59 231.28 125.88 231.08 126.3 230.82 126.68 230.61 126.91 230.38 127.12 230.13 127.29 229.69 127.44 229.38 127.42 229.24 127.36))
  (dk3s_iso_pl '(240.6 159.59 241.24 159.17 241.83 158.67 242.38 158.12 242.97 157.41 243.49 156.64 243.95 155.83 244.33 154.98 244.58 154.25 244.8 153.35 244.91 152.58 244.92 151.81 244.85 151.2 244.69 150.6 244.42 150.04 244.24 149.79 244.03 149.57 243.66 149.29))
  (dk3s_iso_pl '(237.53 159.9 237.81 160.03 238.1 160.12 238.41 160.17 238.87 160.18 239.32 160.11 239.76 159.98 240.19 159.81 240.6 159.59))
  (dk3s_iso_pl '(230.16 153.57 230.8 153.14 231.4 152.65 231.94 152.1 232.53 151.38 233.06 150.61 233.51 149.8 233.89 148.96 234.14 148.23 234.37 147.33 234.47 146.56 234.48 145.79 234.41 145.17 234.25 144.57 233.99 144.02 233.81 143.77 233.59 143.54 233.22 143.27))
  (dk3s_iso_pl '(233.22 143.27 232.8 143.08 232.5 143.01 232.19 142.98 231.57 143.03 230.98 143.19 230.27 143.51 229.62 143.92 229.02 144.41 228.36 145.06))
  (dk3s_iso_pl '(226.42 148.22 226.12 149.09 225.92 149.99 225.83 150.91 225.86 151.68 226.02 152.43 226.26 152.99 226.62 153.49 226.84 153.7 227.1 153.87))
  (dk3s_iso_pl '(227.1 153.87 227.37 154.01 227.67 154.1 227.97 154.15 228.43 154.15 228.88 154.08 229.33 153.96 229.75 153.78 230.16 153.57))
  (dk3s_iso_pl '(241.9 159.34 242.29 159.09 242.77 158.71 243.22 158.28 243.63 157.81 244 157.31 244.33 156.78 244.62 156.24 244.87 155.67 245.08 155.08 245.23 154.48 245.33 153.87 245.36 153.41 245.34 152.94 245.27 152.48 245.13 152.04 244.91 151.63))
  (dk3s_iso_pl '(240.18 159.81 240.51 159.81 240.99 159.73 241.46 159.56 241.9 159.34))
  (dk3s_iso_pl '(241.9 160.34 242.54 159.92 243.13 159.42 243.68 158.87 244.27 158.16 244.79 157.39 245.24 156.58 245.62 155.73 245.88 155 246.1 154.1 246.21 153.33 246.22 152.56 246.15 151.95 245.99 151.35 245.72 150.79 245.54 150.54 245.33 150.32 244.96 150.04))
  (dk3s_iso_pl '(244.96 150.04 244.68 149.91 244.24 149.79))
  (dk3s_iso_pl '(238.25 160.15 238.58 160.47 238.83 160.65))
  (dk3s_iso_pl '(238.83 160.65 239.11 160.78 239.4 160.87 239.7 160.92 240.16 160.93 240.62 160.86 241.06 160.73 241.49 160.56 241.9 160.34))
  (dk3s_iso_pl '(256.62 168.84 257.26 168.42 257.86 167.92 258.4 167.37 258.99 166.66 259.51 165.89 259.97 165.08 260.35 164.23 260.6 163.5 260.82 162.6 260.93 161.83 260.94 161.06 260.87 160.45 260.71 159.85 260.44 159.29 260.26 159.04 260.05 158.82 259.68 158.54))
  (dk3s_iso_pl '(253.56 169.15 253.83 169.28 254.12 169.37 254.43 169.42 254.89 169.43 255.34 169.36 255.78 169.23 256.21 169.06 256.62 168.84))
  (dk3s_iso_pl '(263.98 169.72 264.36 169.44 264.78 168.96 265.11 168.42 265.28 167.97 265.37 167.5 265.37 167.03 265.28 166.72 265.2 166.59 264.97 166.37))
  (dk3s_iso_pl '(262.98 169.82 263.14 169.88 263.49 169.9 263.66 169.86 263.98 169.72))
  (dk3s_iso_pl '(270.47 172.47 270.71 172.27 270.89 172.01 271 171.71 271 171.4))
  (dk3s_iso_pl '(271 171.4 270.86 171.18))
  (dk3s_iso_pl '(270.09 172.51 270.35 172.52))
  (dk3s_iso_pl '(270.35 172.52 270.47 172.47))
  (dk3s_iso_pl '(270.91 172.34 271.03 172.23 271.1 172.08 271.12 171.92))
  (dk3s_iso_pl '(270.86 172.37 270.91 172.34))
  (dk3s_iso_pl '(240.6 136.79 241.24 136.37 241.83 135.87 242.38 135.32 242.97 134.61 243.49 133.84 243.95 133.03 244.33 132.18 244.58 131.45 244.8 130.55 244.91 129.78 244.92 129.01 244.85 128.4 244.69 127.8 244.42 127.24 244.24 126.99 244.03 126.77 243.66 126.49))
  (dk3s_iso_pl '(237.53 137.1 237.81 137.23 238.1 137.32 238.41 137.37 238.87 137.38 239.32 137.31 239.76 137.18 240.19 137.01 240.6 136.79))
  (dk3s_iso_pl '(230.16 130.77 230.8 130.34 231.4 129.85 231.94 129.3 232.53 128.58 233.06 127.81 233.51 127 233.89 126.16 234.14 125.43 234.37 124.53 234.47 123.76 234.48 122.99 234.41 122.37 234.25 121.77 233.99 121.22 233.81 120.97 233.59 120.74 233.22 120.47))
  (dk3s_iso_pl '(233.22 120.47 232.94 120.33 232.65 120.24 232.03 120.18 231.42 120.26 230.68 120.5 230 120.87 229.24 121.41 228.56 122.05 227.95 122.75))
  (dk3s_iso_pl '(226.19 126.05 225.96 126.96 225.85 127.74 225.84 128.52 225.9 129.14 226.06 129.74 226.33 130.31 226.51 130.56 226.72 130.79 227.1 131.07))
  (dk3s_iso_pl '(227.1 131.07 227.37 131.21 227.67 131.3 227.97 131.35 228.43 131.35 228.88 131.28 229.33 131.16 229.75 130.98 230.16 130.77))
  (dk3s_iso_pl '(241.9 136.54 242.29 136.29 242.77 135.91 243.22 135.48 243.63 135.01 244 134.51 244.33 133.98 244.62 133.44 244.87 132.87 245.08 132.28 245.23 131.68 245.33 131.07 245.36 130.61 245.34 130.14 245.27 129.68 245.13 129.24 244.91 128.83))
  (dk3s_iso_pl '(240.18 137.01 240.51 137.01 240.99 136.93 241.46 136.76 241.9 136.54))
  (dk3s_iso_pl '(241.9 137.54 242.54 137.12 243.13 136.62 243.68 136.07 244.27 135.36 244.79 134.59 245.24 133.78 245.62 132.93 245.88 132.2 246.1 131.3 246.21 130.53 246.22 129.76 246.15 129.15 245.99 128.55 245.72 127.99 245.54 127.74 245.33 127.52 244.96 127.24))
  (dk3s_iso_pl '(244.96 127.24 244.68 127.11 244.24 126.99))
  (dk3s_iso_pl '(238.25 137.35 238.58 137.67 238.83 137.85))
  (dk3s_iso_pl '(238.83 137.85 239.11 137.98 239.4 138.07 239.7 138.12 240.16 138.13 240.62 138.06 241.06 137.93 241.49 137.76 241.9 137.54))
  (dk3s_iso_pl '(256.62 146.04 257.26 145.62 257.86 145.12 258.4 144.57 258.99 143.86 259.51 143.09 259.97 142.28 260.35 141.43 260.6 140.7 260.82 139.8 260.93 139.03 260.94 138.26 260.87 137.65 260.71 137.05 260.44 136.49 260.26 136.24 260.05 136.02 259.68 135.74))
  (dk3s_iso_pl '(253.56 146.35 253.83 146.48 254.12 146.57 254.43 146.62 254.89 146.63 255.34 146.56 255.78 146.43 256.21 146.26 256.62 146.04))
  (dk3s_iso_pl '(263.98 146.92 264.36 146.64 264.78 146.16 265.11 145.62 265.28 145.17 265.37 144.7 265.37 144.23 265.28 143.92 265.2 143.79 264.97 143.57))
  (dk3s_iso_pl '(262.98 147.02 263.14 147.08 263.49 147.1 263.66 147.06 263.98 146.92))
  (dk3s_iso_pl '(270.47 149.67 270.71 149.47 270.89 149.21 271 148.91 271 148.6))
  (dk3s_iso_pl '(271 148.6 270.86 148.38))
  (dk3s_iso_pl '(270.09 149.71 270.35 149.72))
  (dk3s_iso_pl '(270.35 149.72 270.47 149.67))
  (dk3s_iso_pl '(270.91 149.54 271.03 149.43 271.1 149.28 271.12 149.12))
  (dk3s_iso_pl '(270.86 149.57 270.91 149.54))
  (dk3s_iso_pl '(213.71 115.21 213.85 115.12 214.08 114.88 214.31 114.43 214.36 114.11 214.35 113.94 214.29 113.79 214.17 113.67))
  (dk3s_iso_pl '(213.25 115.26 213.41 115.3 213.57 115.28 213.71 115.21))
  (dk3s_iso_pl '(213.71 116.46 214.22 116.09 214.64 115.62 215.06 114.95 215.3 114.37 215.43 113.75 215.45 113.44 215.42 113.12 215.26 112.68 215.07 112.43 214.94 112.34))
  (dk3s_iso_pl '(214.94 112.34 214.8 112.28 214.5 112.23 214.04 112.31 213.76 112.44 213.5 112.6 213.04 113.01))
  (dk3s_iso_pl '(212.12 114.6 212 115.21 211.98 115.52 212.01 115.82 212.17 116.26 212.36 116.5 212.49 116.59))
  (dk3s_iso_pl '(212.49 116.59 212.79 116.69 213.11 116.69 213.42 116.6 213.71 116.46))
  (dk3s_iso_pl '(214.58 116.96 215.08 116.59 215.51 116.12 215.92 115.45 216.16 114.87 216.3 114.25 216.31 113.94 216.28 113.62 216.13 113.18 215.93 112.93 215.8 112.84))
  (dk3s_iso_pl '(213.36 117.09 213.66 117.19 213.98 117.19 214.29 117.1 214.58 116.96))
  (dk3s_iso_pl '(220.64 120.09 221.03 119.81 221.45 119.33 221.77 118.79 221.94 118.34 222.04 117.88 222.03 117.4 221.94 117.1 221.87 116.96 221.64 116.74))
  (dk3s_iso_pl '(219.65 120.19 219.81 120.25 220.15 120.27 220.32 120.23 220.64 120.09))
  (dk3s_iso_pl '(227.14 122.84 227.38 122.64 227.55 122.38 227.66 122.08 227.66 121.77))
  (dk3s_iso_pl '(227.66 121.77 227.52 121.55))
  (dk3s_iso_pl '(227.57 122.71 227.69 122.6 227.77 122.45 227.78 122.29))
  (dk3s_iso_pl '(11.49 17.22 6.47 14.32))
  (dk3s_iso_pl '(12.11 16.16 7.08 13.26))
  (dk3s_iso_pl '(6.47 14.32 6.21 14.14 5.85 13.83 5.55 13.46 5.29 13.06 5.09 12.62 4.98 12.32 4.89 11.86 4.87 11.54))
  (dk3s_iso_pl '(7.08 13.26 6.72 12.96 6.43 12.58 6.28 12.3 6.17 12.01 6.09 11.54))
  (dk3s_iso_pl '(4.87 11.54 4.87 6.89))
  (dk3s_iso_pl '(6.09 11.54 6.09 6.89))
  (dk3s_iso_pl '(0.84 8.51 4.87 6.19))
  (dk3s_iso_pl '(1.45 9.57 4.87 7.6))
  (dk3s_iso_pl '(5.48 5.83 9.5 3.51))
  (dk3s_iso_pl '(6.09 6.89 10.11 4.57))
  (dk3s_iso_pl '(0.84 11.07 0.47 10.8 0.27 10.57 0.06 10.17 0 9.87 0.02 9.56 0.18 9.13 0.47 8.78 0.84 8.51))
  (dk3s_iso_pl '(1.45 10.01 1.32 9.92 1.22 9.79 1.32 9.66 1.45 9.57))
  (dk3s_iso_pl '(4.87 6.19 4.87 1.54))
  (dk3s_iso_pl '(6.09 5.48 6.09 1.54))
  (dk3s_iso_pl '(9.5 3.51 9.79 3.37 10.24 3.22 10.71 3.14 11.19 3.12 11.66 3.16 11.97 3.22 12.43 3.37 12.71 3.51))
  (dk3s_iso_pl '(10.11 4.57 10.56 4.4 10.87 4.35 11.19 4.34 11.66 4.4 12.1 4.57))
  (dk3s_iso_pl '(5.86 13.97 0.84 11.07))
  (dk3s_iso_pl '(4.91 12 1.45 10.01))
  (dk3s_iso_pl '(5.55 0.17 5.85 0.04 6.33 0.01 6.64 0.07 7.08 0.26))
  (dk3s_iso_pl '(4.87 1.54 4.92 1.06 5.02 0.76 5.3 0.36 5.55 0.17))
  (dk3s_iso_pl '(6.09 1.54 6.1 1.38 6.16 1.23 6.32 1.25 6.47 1.32))
  (dk3s_iso_pl '(12.71 3.51 17.74 6.41))
  (dk3s_iso_pl '(12.1 4.57 17.12 7.47))
  (dk3s_iso_pl '(7.08 0.26 12.11 3.16))
  (dk3s_iso_pl '(6.47 1.32 9.93 3.31))
  (dk3s_iso_pl '(10.94 9.4 12.55 8.91))
  (dk3s_iso_pl '(10.47 10.21 10.86 11.89))
  (dk3s_iso_pl '(15.95 10.36 21.36 13.48))
  (dk3s_iso_pl '(13.8 14.07 19.22 17.2))
  (dk3s_iso_pl '(10.2 9.02 11.19 9.59))
  (dk3s_iso_pl '(9.77 9.76 10.76 10.34))
  (dk3s_iso_pl '(16.7 1.7 107.83 54.32))
  (dk3s_iso_pl '(6.9 18.67 98.04 71.29))
  (dk3s_iso_pl '(126.14 55.34 129.17 57.09))
  (dk3s_iso_pl '(108.08 86.63 111.11 88.38))
  (dk3s_iso_pl '(109.25 51.6 121.37 58.6))
  (dk3s_iso_pl '(96.39 73.88 108.51 80.88))
  (dk3s_iso_pl '(144.18 79.26 144.46 79.42))
  (dk3s_iso_pl '(137.81 90.29 138.09 90.45))
  (dk3s_iso_pl '(21.75 14.04 103.82 58.45))
  (dk3s_iso_pl '(19.94 17.24 102.06 61.67))
  (dk3s_iso_pl '(103.82 58.45 103.87 58.47))
  (dk3s_iso_pl '(103.87 58.47 104.04 58.57))
  (dk3s_iso_pl '(102.05 61.67 143.08 85.35))
  (dk3s_iso_pl '(145.77 82.84 148.55 85.22))
  (dk3s_iso_pl '(143.02 85.32 146.24 88.08))
  (dk3s_iso_pl '(146.52 88.27 146.24 88.08))
  (dk3s_iso_pl '(153.61 88.12 166.86 95.77))
  (dk3s_iso_pl '(170.15 97.67 210.25 120.82))
  (dk3s_iso_pl '(213.54 122.72 216.99 124.71))
  (dk3s_iso_pl '(152.46 91.7 165.91 99.47))
  (dk3s_iso_pl '(169.2 101.37 209.3 124.52))
  (dk3s_iso_pl '(212.59 126.42 215.15 127.9))
  (dk3s_iso_pl '(166.04 94.43 169.33 96.33))
  (dk3s_iso_pl '(161.88 101.65 165.17 103.55))
  (dk3s_iso_pl '(209.43 119.48 212.72 121.38))
  (dk3s_iso_pl '(205.27 126.7 208.56 128.6))
  (dk3s_iso_pl '(148.31 83.35 152.6 85.82))
  (dk3s_iso_pl '(143.41 91.83 147.7 94.31))
  (dk3s_iso_pl '(217.29 124.18 218.16 124.68))
  (dk3s_iso_pl '(214.84 128.43 215.71 128.93))
  (dk3s_iso_pl '(218.64 125.49 223.99 128.58))
  (dk3s_iso_pl '(216.65 128.94 222 132.03))
  (dk3s_iso_pl '(224.3 130.17 229.87 133.39))
  (dk3s_iso_pl '(223.53 131.5 229.11 134.72))
  (dk3s_iso_pl '(230.14 134.13 230.02 133.61))
  (dk3s_iso_pl '(229.88 134.58 229.37 134.73))
  (dk3s_iso_pl '(39.67 27.92 100.46 63.01))
  (dk3s_iso_pl '(20.26 20.95 98.63 66.2))
  (dk3s_iso_pl '(141.7 86.7 145.6 87.86))
  (dk3s_iso_pl '(140.96 90.31 144.41 91.34))
  (dk3s_iso_pl '(152.44 91.75 165.88 99.51))
  (dk3s_iso_pl '(169.17 101.41 209.27 124.56))
  (dk3s_iso_pl '(149.58 94.34 162.56 101.84))
  (dk3s_iso_pl '(165.86 103.74 205.95 126.89))
  (dk3s_iso_pl '(209.24 128.79 209.45 128.91))
  (dk3s_iso_pl '(209.45 128.91 210.75 129.74 211.98 130.67 213.25 131.78 214.44 132.99 215.55 134.26 216.68 135.72 217.72 137.25 218.66 138.84))
  (dk3s_iso_pl '(212.53 126.5 213.78 127.41 215.09 128.49 216.33 129.66 217.6 131.01 218.79 132.43 219.9 133.91 220.93 135.45 221.87 137.05))
  (dk3s_iso_pl '(221.87 137.05 222.82 138.64 223.85 140.16 224.98 141.63 226.09 142.9 227.29 144.1 228.56 145.22 229.78 146.15 231.08 146.98))
  (dk3s_iso_pl '(218.66 138.84 219.76 140.68 220.89 142.34 222.11 143.92 223.42 145.42 224.83 146.84 226.22 148.06 227.69 149.17 229.24 150.16))
  (dk3s_iso_pl '(22.09 13 55.81 32.47))
  (dk3s_iso_pl '(54.01 35.68 98.63 61.43))
  (dk3s_iso_pl '(141.7 86.46 142.36 86.89))
  (dk3s_iso_pl '(214.01 127.59 214.37 127.66))
  (dk3s_iso_pl '(220.84 126.76 221.26 126.52))
  (dk3s_iso_pl '(216.06 124.18 216.3 124.19))
  (dk3s_iso_pl '(217.22 124.14 217.84 124.03 218.29 123.9 218.87 123.66 219.27 123.42))
  (dk3s_iso_pl '(219.27 123.42 220.08 122.97 221.07 122.56 221.96 122.3 223.02 122.13 224.09 122.07 225.16 122.13 226.23 122.29 227.42 122.58))
  (dk3s_iso_pl '(227.65 122.65 228.54 122.96 229.41 123.32 230.25 123.73 231.08 124.18))
  (dk3s_iso_pl '(221.26 126.52 221.93 126.16 222.37 126 222.81 125.88 223.72 125.76 224.18 125.75 224.79 125.79 225.85 125.97 227.02 126.32 228.16 126.79 229.24 127.36))
  (dk3s_iso_pl '(233.22 143.27 243.66 149.29))
  (dk3s_iso_pl '(227.1 153.87 237.53 159.9))
  (dk3s_iso_pl '(244.96 150.04 259.68 158.54))
  (dk3s_iso_pl '(238.83 160.65 253.56 169.15))
  (dk3s_iso_pl '(260.51 163.79 264.97 166.37))
  (dk3s_iso_pl '(258.52 167.24 262.98 169.82))
  (dk3s_iso_pl '(265.28 167.96 270.86 171.18))
  (dk3s_iso_pl '(264.51 169.29 270.09 172.51))
  (dk3s_iso_pl '(271.12 171.92 271 171.4))
  (dk3s_iso_pl '(270.86 172.37 270.35 172.52))
  (dk3s_iso_pl '(233.22 120.47 243.66 126.49))
  (dk3s_iso_pl '(227.1 131.07 237.53 137.1))
  (dk3s_iso_pl '(244.96 127.24 259.68 135.74))
  (dk3s_iso_pl '(238.83 137.85 253.56 146.35))
  (dk3s_iso_pl '(260.51 140.99 264.97 143.57))
  (dk3s_iso_pl '(258.52 144.44 262.98 147.02))
  (dk3s_iso_pl '(265.28 145.16 270.86 148.38))
  (dk3s_iso_pl '(264.51 146.49 270.09 149.71))
  (dk3s_iso_pl '(271.12 149.12 271 148.6))
  (dk3s_iso_pl '(270.86 149.57 270.35 149.72))
  (dk3s_iso_pl '(138.55 70.01 139.85 70.76))
  (dk3s_iso_pl '(145.02 73.74 214.17 113.67))
  (dk3s_iso_pl '(145.4 76.08 213.25 115.26))
  (dk3s_iso_pl '(214.94 112.34 215.8 112.84))
  (dk3s_iso_pl '(212.49 116.59 213.36 117.09))
  (dk3s_iso_pl '(216.29 113.65 221.64 116.74))
  (dk3s_iso_pl '(214.3 117.1 219.65 120.19))
  (dk3s_iso_pl '(221.94 118.33 227.52 121.55))
  (dk3s_iso_pl '(221.18 119.66 225.54 122.18))
  (dk3s_iso_pl '(227.78 122.29 227.66 121.77))
  (dk3s_iso_ln 18.77 7.21 20.5 7.21 g_dk3s_lay_thin)
  (dk3s_iso_ln 19.63 7.71 21.36 7.71 g_dk3s_lay_thin)
  (dk3s_iso_ln 20.49 8.2 21.21 8.2 g_dk3s_lay_thin)
  (dk3s_iso_ln 23.9 9.65 24.73 9.65 g_dk3s_lay_thin)
  (dk3s_iso_ln 23.86 10.15 25.59 10.15 g_dk3s_lay_thin)
  (dk3s_iso_ln 24.71 10.64 26.44 10.64 g_dk3s_lay_thin)
  (dk3s_iso_ln 25.57 11.14 27.3 11.14 g_dk3s_lay_thin)
  (dk3s_iso_ln 26.43 11.63 28.16 11.63 g_dk3s_lay_thin)
  (dk3s_iso_ln 27.28 12.13 29.02 12.13 g_dk3s_lay_thin)
  (dk3s_iso_ln 28.14 12.62 29.87 12.62 g_dk3s_lay_thin)
  (dk3s_iso_ln 29 13.12 30.02 13.12 g_dk3s_lay_thin)
  (dk3s_iso_ln 32.56 14.65 33.39 14.65 g_dk3s_lay_thin)
  (dk3s_iso_ln 32.52 15.15 34.25 15.15 g_dk3s_lay_thin)
  (dk3s_iso_ln 33.37 15.64 35.1 15.64 g_dk3s_lay_thin)
  (dk3s_iso_ln 34.23 16.14 35.96 16.14 g_dk3s_lay_thin)
  (dk3s_iso_ln 35.09 16.63 36.82 16.63 g_dk3s_lay_thin)
  (dk3s_iso_ln 35.94 17.13 37.68 17.13 g_dk3s_lay_thin)
  (dk3s_iso_ln 36.8 17.62 38.53 17.62 g_dk3s_lay_thin)
  (dk3s_iso_ln 37.66 18.12 38.68 18.12 g_dk3s_lay_thin)
  (dk3s_iso_ln 41.27 19.63 42 19.63 g_dk3s_lay_thin)
  (dk3s_iso_ln 41.13 20.12 42.86 20.12 g_dk3s_lay_thin)
  (dk3s_iso_ln 41.99 20.62 43.72 20.62 g_dk3s_lay_thin)
  (dk3s_iso_ln 42.84 21.11 44.58 21.11 g_dk3s_lay_thin)
  (dk3s_iso_ln 43.7 21.61 45.43 21.61 g_dk3s_lay_thin)
  (dk3s_iso_ln 44.56 22.1 46.29 22.1 g_dk3s_lay_thin)
  (dk3s_iso_ln 45.42 22.6 47.15 22.6 g_dk3s_lay_thin)
  (dk3s_iso_ln 46.27 23.09 48.01 23.09 g_dk3s_lay_thin)
  (dk3s_iso_ln 47.13 23.59 48.86 23.59 g_dk3s_lay_thin)
  (dk3s_iso_ln 47.99 24.08 49.72 24.08 g_dk3s_lay_thin)
  (dk3s_iso_ln 48.84 24.58 50.58 24.58 g_dk3s_lay_thin)
  (dk3s_iso_ln 49.7 25.07 51.43 25.07 g_dk3s_lay_thin)
  (dk3s_iso_ln 50.56 25.57 52.29 25.57 g_dk3s_lay_thin)
  (dk3s_iso_ln 51.42 26.06 53.15 26.06 g_dk3s_lay_thin)
  (dk3s_iso_ln 52.27 26.56 54.01 26.56 g_dk3s_lay_thin)
  (dk3s_iso_ln 53.13 27.05 54.86 27.05 g_dk3s_lay_thin)
  (dk3s_iso_ln 53.99 27.55 55.72 27.55 g_dk3s_lay_thin)
  (dk3s_iso_ln 54.85 28.04 56.58 28.04 g_dk3s_lay_thin)
  (dk3s_iso_ln 55.7 28.54 57.44 28.54 g_dk3s_lay_thin)
  (dk3s_iso_ln 56.56 29.03 58.29 29.03 g_dk3s_lay_thin)
  (dk3s_iso_ln 57.42 29.53 59.15 29.53 g_dk3s_lay_thin)
  (dk3s_iso_ln 58.28 30.02 60.01 30.02 g_dk3s_lay_thin)
  (dk3s_iso_ln 59.13 30.52 60.86 30.52 g_dk3s_lay_thin)
  (dk3s_iso_ln 59.99 31.01 61.72 31.01 g_dk3s_lay_thin)
  (dk3s_iso_ln 60.85 31.51 62.58 31.51 g_dk3s_lay_thin)
  (dk3s_iso_ln 61.7 32 63.44 32 g_dk3s_lay_thin)
  (dk3s_iso_ln 62.56 32.5 64.29 32.5 g_dk3s_lay_thin)
  (dk3s_iso_ln 63.42 32.99 65.15 32.99 g_dk3s_lay_thin)
  (dk3s_iso_ln 64.28 33.49 66.01 33.49 g_dk3s_lay_thin)
  (dk3s_iso_ln 65.13 33.98 66.87 33.98 g_dk3s_lay_thin)
  (dk3s_iso_ln 65.99 34.48 67.72 34.48 g_dk3s_lay_thin)
  (dk3s_iso_ln 66.85 34.97 68.58 34.97 g_dk3s_lay_thin)
  (dk3s_iso_ln 67.71 35.47 69.44 35.47 g_dk3s_lay_thin)
  (dk3s_iso_ln 68.56 35.96 70.3 35.96 g_dk3s_lay_thin)
  (dk3s_iso_ln 69.42 36.46 71.15 36.46 g_dk3s_lay_thin)
  (dk3s_iso_ln 70.28 36.95 72.01 36.95 g_dk3s_lay_thin)
  (dk3s_iso_ln 71.14 37.45 72.87 37.45 g_dk3s_lay_thin)
  (dk3s_iso_ln 71.99 37.94 73.72 37.94 g_dk3s_lay_thin)
  (dk3s_iso_ln 72.85 38.44 74.58 38.44 g_dk3s_lay_thin)
  (dk3s_iso_ln 73.71 38.93 75.44 38.93 g_dk3s_lay_thin)
  (dk3s_iso_ln 74.56 39.43 76.3 39.43 g_dk3s_lay_thin)
  (dk3s_iso_ln 75.42 39.92 77.15 39.92 g_dk3s_lay_thin)
  (dk3s_iso_ln 76.28 40.42 78.01 40.42 g_dk3s_lay_thin)
  (dk3s_iso_ln 77.14 40.91 78.87 40.91 g_dk3s_lay_thin)
  (dk3s_iso_ln 77.99 41.41 79.73 41.41 g_dk3s_lay_thin)
  (dk3s_iso_ln 78.85 41.9 80.58 41.9 g_dk3s_lay_thin)
  (dk3s_iso_ln 79.71 42.4 81.44 42.4 g_dk3s_lay_thin)
  (dk3s_iso_ln 80.57 42.89 82.3 42.89 g_dk3s_lay_thin)
  (dk3s_iso_ln 81.42 43.39 83.16 43.39 g_dk3s_lay_thin)
  (dk3s_iso_ln 82.28 43.88 84.01 43.88 g_dk3s_lay_thin)
  (dk3s_iso_ln 83.14 44.38 84.87 44.38 g_dk3s_lay_thin)
  (dk3s_iso_ln 84 44.87 85.73 44.87 g_dk3s_lay_thin)
  (dk3s_iso_ln 84.85 45.37 86.58 45.37 g_dk3s_lay_thin)
  (dk3s_iso_ln 85.71 45.86 87.44 45.86 g_dk3s_lay_thin)
  (dk3s_iso_ln 86.57 46.36 88.3 46.36 g_dk3s_lay_thin)
  (dk3s_iso_ln 87.42 46.85 89.16 46.85 g_dk3s_lay_thin)
  (dk3s_iso_ln 88.28 47.35 90.01 47.35 g_dk3s_lay_thin)
  (dk3s_iso_ln 89.14 47.84 90.87 47.84 g_dk3s_lay_thin)
  (dk3s_iso_ln 90 48.34 91.73 48.34 g_dk3s_lay_thin)
  (dk3s_iso_ln 90.85 48.83 92.59 48.83 g_dk3s_lay_thin)
  (dk3s_iso_ln 91.71 49.33 93.44 49.33 g_dk3s_lay_thin)
  (dk3s_iso_ln 92.57 49.82 94.3 49.82 g_dk3s_lay_thin)
  (dk3s_iso_ln 93.43 50.32 95.16 50.32 g_dk3s_lay_thin)
  (dk3s_iso_ln 94.28 50.81 96.02 50.81 g_dk3s_lay_thin)
  (dk3s_iso_ln 95.14 51.31 96.87 51.31 g_dk3s_lay_thin)
  (dk3s_iso_ln 96 51.8 97.73 51.8 g_dk3s_lay_thin)
  (dk3s_iso_ln 96.85 52.3 98.59 52.3 g_dk3s_lay_thin)
  (dk3s_iso_ln 97.71 52.79 99.44 52.79 g_dk3s_lay_thin)
  (dk3s_iso_ln 98.57 53.29 100.3 53.29 g_dk3s_lay_thin)
  (dk3s_iso_ln 99.43 53.78 101.16 53.78 g_dk3s_lay_thin)
  (dk3s_iso_ln 100.28 54.28 102.02 54.28 g_dk3s_lay_thin)
  (dk3s_iso_ln 101.14 54.77 102.87 54.77 g_dk3s_lay_thin)
  (dk3s_iso_ln 102 55.27 103.73 55.27 g_dk3s_lay_thin)
  (dk3s_iso_ln 102.86 55.76 104.59 55.76 g_dk3s_lay_thin)
  (dk3s_iso_ln 103.71 56.26 105.45 56.26 g_dk3s_lay_thin)
  (dk3s_iso_ln 104.57 56.75 106.3 56.75 g_dk3s_lay_thin)
  (dk3s_iso_ln 105.43 57.25 107.16 57.25 g_dk3s_lay_thin)
  (dk3s_iso_ln 106.29 57.74 108.02 57.74 g_dk3s_lay_thin)
  (dk3s_iso_ln 107.14 58.24 108.87 58.24 g_dk3s_lay_thin)
  (dk3s_iso_ln 108 58.73 109.73 58.73 g_dk3s_lay_thin)
  (dk3s_iso_ln 108.86 59.23 110.59 59.23 g_dk3s_lay_thin)
  (dk3s_iso_ln 109.71 59.72 111.45 59.72 g_dk3s_lay_thin)
  (dk3s_iso_ln 110.57 60.22 111.78 60.22 g_dk3s_lay_thin)
  (dk3s_iso_ln 30.38 28.54 30.7 29.1 g_dk3s_lay_thin)
  (dk3s_iso_ln 30.69 28.1 31.56 29.6 g_dk3s_lay_thin)
  (dk3s_iso_ln 31.55 28.59 32.42 30.09 g_dk3s_lay_thin)
  (dk3s_iso_ln 32.41 29.09 33.27 30.59 g_dk3s_lay_thin)
  (dk3s_iso_ln 33.27 29.58 34.13 31.08 g_dk3s_lay_thin)
  (dk3s_iso_ln 34.12 30.08 34.99 31.58 g_dk3s_lay_thin)
  (dk3s_iso_ln 34.98 30.57 35.85 32.07 g_dk3s_lay_thin)
  (dk3s_iso_ln 35.84 31.07 36.7 32.57 g_dk3s_lay_thin)
  (dk3s_iso_ln 36.69 31.56 37.56 33.06 g_dk3s_lay_thin)
  (dk3s_iso_ln 37.55 32.06 38.42 33.56 g_dk3s_lay_thin)
  (dk3s_iso_ln 38.41 32.55 39.28 34.05 g_dk3s_lay_thin)
  (dk3s_iso_ln 39.27 33.05 40.13 34.55 g_dk3s_lay_thin)
  (dk3s_iso_ln 40.12 33.54 40.99 35.04 g_dk3s_lay_thin)
  (dk3s_iso_ln 40.98 34.04 41.85 35.54 g_dk3s_lay_thin)
  (dk3s_iso_ln 41.84 34.53 42.7 36.03 g_dk3s_lay_thin)
  (dk3s_iso_ln 42.7 35.03 43.56 36.53 g_dk3s_lay_thin)
  (dk3s_iso_ln 43.55 35.52 44.42 37.02 g_dk3s_lay_thin)
  (dk3s_iso_ln 44.41 36.02 45.28 37.52 g_dk3s_lay_thin)
  (dk3s_iso_ln 45.27 36.51 46.13 38.01 g_dk3s_lay_thin)
  (dk3s_iso_ln 46.13 37.01 46.99 38.51 g_dk3s_lay_thin)
  (dk3s_iso_ln 46.98 37.5 47.85 39 g_dk3s_lay_thin)
  (dk3s_iso_ln 47.84 38 48.71 39.5 g_dk3s_lay_thin)
  (dk3s_iso_ln 48.7 38.49 49.56 39.99 g_dk3s_lay_thin)
  (dk3s_iso_ln 49.55 38.99 50.42 40.49 g_dk3s_lay_thin)
  (dk3s_iso_ln 50.41 39.48 51.28 40.98 g_dk3s_lay_thin)
  (dk3s_iso_ln 51.27 39.98 52.13 41.48 g_dk3s_lay_thin)
  (dk3s_iso_ln 52.13 40.47 52.99 41.97 g_dk3s_lay_thin)
  (dk3s_iso_ln 52.98 40.97 53.85 42.47 g_dk3s_lay_thin)
  (dk3s_iso_ln 53.84 41.46 54.71 42.96 g_dk3s_lay_thin)
  (dk3s_iso_ln 54.7 41.96 55.56 43.46 g_dk3s_lay_thin)
  (dk3s_iso_ln 55.56 42.45 56.42 43.95 g_dk3s_lay_thin)
  (dk3s_iso_ln 56.41 42.95 57.28 44.45 g_dk3s_lay_thin)
  (dk3s_iso_ln 57.27 43.44 58.14 44.94 g_dk3s_lay_thin)
  (dk3s_iso_ln 58.13 43.94 58.99 45.44 g_dk3s_lay_thin)
  (dk3s_iso_ln 58.98 44.43 59.85 45.93 g_dk3s_lay_thin)
  (dk3s_iso_ln 59.84 44.93 60.71 46.43 g_dk3s_lay_thin)
  (dk3s_iso_ln 60.7 45.42 61.57 46.92 g_dk3s_lay_thin)
  (dk3s_iso_ln 61.56 45.92 62.42 47.42 g_dk3s_lay_thin)
  (dk3s_iso_ln 62.41 46.41 63.28 47.91 g_dk3s_lay_thin)
  (dk3s_iso_ln 63.27 46.91 64.14 48.41 g_dk3s_lay_thin)
  (dk3s_iso_ln 64.13 47.4 64.99 48.9 g_dk3s_lay_thin)
  (dk3s_iso_ln 64.99 47.9 65.85 49.4 g_dk3s_lay_thin)
  (dk3s_iso_ln 65.84 48.39 66.71 49.89 g_dk3s_lay_thin)
  (dk3s_iso_ln 66.7 48.89 67.57 50.39 g_dk3s_lay_thin)
  (dk3s_iso_ln 67.56 49.38 68.42 50.88 g_dk3s_lay_thin)
  (dk3s_iso_ln 68.42 49.88 69.28 51.38 g_dk3s_lay_thin)
  (dk3s_iso_ln 69.27 50.37 70.14 51.87 g_dk3s_lay_thin)
  (dk3s_iso_ln 70.13 50.87 71 52.37 g_dk3s_lay_thin)
  (dk3s_iso_ln 70.99 51.36 71.85 52.86 g_dk3s_lay_thin)
  (dk3s_iso_ln 71.84 51.86 72.71 53.36 g_dk3s_lay_thin)
  (dk3s_iso_ln 72.7 52.35 73.57 53.85 g_dk3s_lay_thin)
  (dk3s_iso_ln 73.56 52.85 74.43 54.35 g_dk3s_lay_thin)
  (dk3s_iso_ln 74.42 53.34 75.28 54.84 g_dk3s_lay_thin)
  (dk3s_iso_ln 75.27 53.84 76.14 55.34 g_dk3s_lay_thin)
  (dk3s_iso_ln 76.13 54.33 77 55.83 g_dk3s_lay_thin)
  (dk3s_iso_ln 76.99 54.83 77.85 56.33 g_dk3s_lay_thin)
  (dk3s_iso_ln 77.85 55.32 78.71 56.82 g_dk3s_lay_thin)
  (dk3s_iso_ln 78.7 55.82 79.57 57.32 g_dk3s_lay_thin)
  (dk3s_iso_ln 79.56 56.31 80.43 57.81 g_dk3s_lay_thin)
  (dk3s_iso_ln 80.42 56.81 81.28 58.31 g_dk3s_lay_thin)
  (dk3s_iso_ln 81.28 57.3 82.14 58.8 g_dk3s_lay_thin)
  (dk3s_iso_ln 82.13 57.8 83 59.3 g_dk3s_lay_thin)
  (dk3s_iso_ln 82.99 58.29 83.86 59.79 g_dk3s_lay_thin)
  (dk3s_iso_ln 83.85 58.79 84.71 60.29 g_dk3s_lay_thin)
  (dk3s_iso_ln 84.7 59.28 85.57 60.78 g_dk3s_lay_thin)
  (dk3s_iso_ln 85.56 59.78 86.43 61.28 g_dk3s_lay_thin)
  (dk3s_iso_ln 86.42 60.27 87.29 61.77 g_dk3s_lay_thin)
  (dk3s_iso_ln 87.28 60.77 88.14 62.27 g_dk3s_lay_thin)
  (dk3s_iso_ln 88.13 61.26 89 62.76 g_dk3s_lay_thin)
  (dk3s_iso_ln 88.99 61.76 89.86 63.26 g_dk3s_lay_thin)
  (dk3s_iso_ln 89.85 62.25 90.71 63.75 g_dk3s_lay_thin)
  (dk3s_iso_ln 90.71 62.75 91.57 64.25 g_dk3s_lay_thin)
  (dk3s_iso_ln 91.56 63.24 92.43 64.74 g_dk3s_lay_thin)
  (dk3s_iso_ln 92.42 63.74 93.29 65.24 g_dk3s_lay_thin)
  (dk3s_iso_ln 93.28 64.23 94.14 65.73 g_dk3s_lay_thin)
  (dk3s_iso_ln 94.14 64.73 95 66.23 g_dk3s_lay_thin)
  (dk3s_iso_ln 94.99 65.22 95.86 66.72 g_dk3s_lay_thin)
  (dk3s_iso_ln 95.85 65.72 96.72 67.22 g_dk3s_lay_thin)
  (dk3s_iso_ln 96.71 66.21 97.57 67.71 g_dk3s_lay_thin)
  (dk3s_iso_ln 97.56 66.71 98.43 68.21 g_dk3s_lay_thin)
  (dk3s_iso_ln 98.42 67.2 99.29 68.7 g_dk3s_lay_thin)
  (dk3s_iso_ln 99.28 67.69 100.14 69.19 g_dk3s_lay_thin)
  (dk3s_iso_ln 100.14 68.19 101 69.69 g_dk3s_lay_thin)
  (dk3s_iso_ln 100.99 68.68 101.86 70.18 g_dk3s_lay_thin)
  (dk3s_iso_ln 101.85 69.18 102.72 70.68 g_dk3s_lay_thin)
  (dk3s_iso_ln 102.71 69.67 103.57 71.17 g_dk3s_lay_thin)
  (dk3s_iso_ln 103.57 70.17 104.43 71.67 g_dk3s_lay_thin)
  (dk3s_iso_ln 104.42 70.66 105.11 71.86 g_dk3s_lay_thin)
  (dk3s_iso_ln 21.72 23.43 22.13 24.15 g_dk3s_lay_thin)
  (dk3s_iso_ln 22.12 23.15 22.99 24.65 g_dk3s_lay_thin)
  (dk3s_iso_ln 22.98 23.64 23.85 25.14 g_dk3s_lay_thin)
  (dk3s_iso_ln 23.84 24.14 24.7 25.64 g_dk3s_lay_thin)
  (dk3s_iso_ln 24.7 24.63 25.56 26.13 g_dk3s_lay_thin)
  (dk3s_iso_ln 25.55 25.13 26.42 26.63 g_dk3s_lay_thin)
  (dk3s_iso_ln 26.41 25.62 27.28 27.12 g_dk3s_lay_thin)
  (dk3s_iso_ln 27.27 26.12 27.78 27 g_dk3s_lay_thin)
  (dk3s_iso_ln 11.8 18.17 11.82 18.2 g_dk3s_lay_thin)
  (dk3s_iso_ln 11.81 17.19 12.67 18.69 g_dk3s_lay_thin)
  (dk3s_iso_ln 12.67 17.69 13.53 19.19 g_dk3s_lay_thin)
  (dk3s_iso_ln 13.52 18.18 14.39 19.68 g_dk3s_lay_thin)
  (dk3s_iso_ln 14.38 18.68 15.25 20.18 g_dk3s_lay_thin)
  (dk3s_iso_ln 15.24 19.17 16.1 20.67 g_dk3s_lay_thin)
  (dk3s_iso_ln 16.1 19.67 16.96 21.17 g_dk3s_lay_thin)
  (dk3s_iso_ln 16.95 20.16 17.82 21.66 g_dk3s_lay_thin)
  (dk3s_iso_ln 17.81 20.66 18.68 22.16 g_dk3s_lay_thin)
  (dk3s_iso_ln 18.67 21.15 19.12 21.93 g_dk3s_lay_thin)
  (dk3s_iso_ln 102.39 72.15 103.11 73.41 g_dk3s_lay_thin)
  (dk3s_iso_ln 102.82 70.79 104.95 74.47 g_dk3s_lay_thin)
  (dk3s_iso_ln 104.66 71.85 106.78 75.53 g_dk3s_lay_thin)
  (dk3s_iso_ln 105.11 70.52 108.62 76.59 g_dk3s_lay_thin)
  (dk3s_iso_ln 105.87 69.7 106.34 70.52 g_dk3s_lay_thin)
  (dk3s_iso_ln 107.86 73.15 110.46 77.65 g_dk3s_lay_thin)
  (dk3s_iso_ln 109.7 74.21 112.29 78.71 g_dk3s_lay_thin)
  (dk3s_iso_ln 111.53 75.27 114.13 79.77 g_dk3s_lay_thin)
  (dk3s_iso_ln 117.11 84.93 117.81 86.15 g_dk3s_lay_thin)
  (dk3s_iso_ln 113.37 76.33 115.32 79.71 g_dk3s_lay_thin)
  (dk3s_iso_ln 117.11 82.81 119.65 87.21 g_dk3s_lay_thin)
  (dk3s_iso_ln 115.21 77.39 120.14 85.93 g_dk3s_lay_thin)
  (dk3s_iso_ln 117.05 78.45 121.81 86.7 g_dk3s_lay_thin)
  (dk3s_iso_ln 119.75 81.01 123.65 87.76 g_dk3s_lay_thin)
  (dk3s_iso_ln 121.39 81.74 125.48 88.82 g_dk3s_lay_thin)
  (dk3s_iso_ln 123.23 82.8 127.32 89.88 g_dk3s_lay_thin)
  (dk3s_iso_ln 125.06 83.86 128.46 89.73 g_dk3s_lay_thin)
  (dk3s_iso_ln 126.9 84.92 128.8 88.21 g_dk3s_lay_thin)
  (dk3s_iso_ln 128.74 85.98 128.8 86.08 g_dk3s_lay_thin)
  (dk3s_iso_ln 110.76 57.66 112.2 57.66 g_dk3s_lay_thin)
  (dk3s_iso_ln 109.8 58.72 114.04 58.72 g_dk3s_lay_thin)
  (dk3s_iso_ln 111.63 59.78 115.88 59.78 g_dk3s_lay_thin)
  (dk3s_iso_ln 110.7 60.84 117.71 60.84 g_dk3s_lay_thin)
  (dk3s_iso_ln 110.37 61.9 111.31 61.9 g_dk3s_lay_thin)
  (dk3s_iso_ln 114.35 61.9 119.55 61.9 g_dk3s_lay_thin)
  (dk3s_iso_ln 116.19 62.96 121.39 62.96 g_dk3s_lay_thin)
  (dk3s_iso_ln 118.03 64.02 123.23 64.02 g_dk3s_lay_thin)
  (dk3s_iso_ln 129.18 64.02 130.59 64.02 g_dk3s_lay_thin)
  (dk3s_iso_ln 119.87 65.08 123.76 65.08 g_dk3s_lay_thin)
  (dk3s_iso_ln 127.34 65.08 132.42 65.08 g_dk3s_lay_thin)
  (dk3s_iso_ln 121.7 66.14 131.57 66.14 g_dk3s_lay_thin)
  (dk3s_iso_ln 123.54 67.2 130.05 67.2 g_dk3s_lay_thin)
  (dk3s_iso_ln 127.11 68.26 131.89 68.26 g_dk3s_lay_thin)
  (dk3s_iso_ln 128.56 69.32 133.72 69.32 g_dk3s_lay_thin)
  (dk3s_iso_ln 130.39 70.38 135.56 70.38 g_dk3s_lay_thin)
  (dk3s_iso_ln 132.23 71.44 137.4 71.44 g_dk3s_lay_thin)
  (dk3s_iso_ln 134.07 72.51 137.86 72.51 g_dk3s_lay_thin)
  (dk3s_iso_ln 135.91 73.57 136.03 73.57 g_dk3s_lay_thin)
  (dk3s_iso_ln 131.22 71.74 132.71 71.74 g_dk3s_lay_thin)
  (dk3s_iso_ln 129.87 72.52 134.05 72.52 g_dk3s_lay_thin)
  (dk3s_iso_ln 130.16 73.3 135.4 73.3 g_dk3s_lay_thin)
  (dk3s_iso_ln 131.51 74.08 136.75 74.08 g_dk3s_lay_thin)
  (dk3s_iso_ln 132.86 74.86 138.1 74.86 g_dk3s_lay_thin)
  (dk3s_iso_ln 134.2 75.63 138.85 75.63 g_dk3s_lay_thin)
  (dk3s_iso_ln 135.55 76.41 139.49 76.41 g_dk3s_lay_thin)
  (dk3s_iso_ln 140.45 76.41 141.88 76.41 g_dk3s_lay_thin)
  (dk3s_iso_ln 136.9 77.19 143.22 77.19 g_dk3s_lay_thin)
  (dk3s_iso_ln 138.25 77.97 144.57 77.97 g_dk3s_lay_thin)
  (dk3s_iso_ln 139.59 78.75 145.07 78.75 g_dk3s_lay_thin)
  (dk3s_iso_ln 140.94 79.52 143.72 79.52 g_dk3s_lay_thin)
  (dk3s_iso_ln 142.29 80.3 142.38 80.3 g_dk3s_lay_thin)
  (dk3s_iso_ln 124.82 82.83 125.56 84.12 g_dk3s_lay_thin)
  (dk3s_iso_ln 124.82 81.27 126.91 84.9 g_dk3s_lay_thin)
  (dk3s_iso_ln 125.64 81.14 128.26 85.68 g_dk3s_lay_thin)
  (dk3s_iso_ln 126.98 81.92 129.6 86.45 g_dk3s_lay_thin)
  (dk3s_iso_ln 128.33 82.69 130.95 87.23 g_dk3s_lay_thin)
  (dk3s_iso_ln 129.68 83.47 132 87.5 g_dk3s_lay_thin)
  (dk3s_iso_ln 133.48 90.05 134.03 91.01 g_dk3s_lay_thin)
  (dk3s_iso_ln 131.03 84.25 133 87.66 g_dk3s_lay_thin)
  (dk3s_iso_ln 133.48 88.49 135.38 91.79 g_dk3s_lay_thin)
  (dk3s_iso_ln 132.37 85.03 136.73 92.56 g_dk3s_lay_thin)
  (dk3s_iso_ln 133.72 85.8 137.51 92.36 g_dk3s_lay_thin)
  (dk3s_iso_ln 135.07 86.58 137.81 91.33 g_dk3s_lay_thin)
  (dk3s_iso_ln 136.42 87.36 137.81 89.77 g_dk3s_lay_thin)
  (dk3s_iso_ln 137.76 88.14 137.81 88.22 g_dk3s_lay_thin)
  (dk3s_iso_ln 123.34 79.76 124.67 82.07 g_dk3s_lay_thin)
  (dk3s_iso_ln 124.01 80.15 124.82 81.54 g_dk3s_lay_thin)
  (dk3s_iso_ln 124.68 80.54 124.82 80.77 g_dk3s_lay_thin)
  (dk3s_iso_ln 127.82 72 130.49 72 g_dk3s_lay_thin)
  (dk3s_iso_ln 128.49 72.39 130.1 72.39 g_dk3s_lay_thin)
  (dk3s_iso_ln 129.17 72.78 129.43 72.78 g_dk3s_lay_thin)
  (dk3s_iso_ln 124.69 68.76 126.03 68.76 g_dk3s_lay_thin)
  (dk3s_iso_ln 124.2 69.33 127.01 69.33 g_dk3s_lay_thin)
  (dk3s_iso_ln 124.22 69.89 127.99 69.89 g_dk3s_lay_thin)
  (dk3s_iso_ln 125.2 70.46 128.96 70.46 g_dk3s_lay_thin)
  (dk3s_iso_ln 126.18 71.02 128.57 71.02 g_dk3s_lay_thin)
  (dk3s_iso_ln 127.16 71.59 127.59 71.59 g_dk3s_lay_thin)
  (dk3s_iso_ln 118.97 78.67 119.64 79.82 g_dk3s_lay_thin)
  (dk3s_iso_ln 119.21 77.96 120.62 80.39 g_dk3s_lay_thin)
  (dk3s_iso_ln 119.71 77.69 121.6 80.96 g_dk3s_lay_thin)
  (dk3s_iso_ln 120.69 78.26 122.58 81.52 g_dk3s_lay_thin)
  (dk3s_iso_ln 121.67 78.82 122.87 80.89 g_dk3s_lay_thin)
  (dk3s_iso_ln 122.65 79.39 122.87 79.76 g_dk3s_lay_thin)
  (dk3s_iso_ln 100.57 65.62 101.39 67.04 g_dk3s_lay_thin)
  (dk3s_iso_ln 101.05 64.76 102.86 67.89 g_dk3s_lay_thin)
  (dk3s_iso_ln 102.52 65.61 104.33 68.73 g_dk3s_lay_thin)
  (dk3s_iso_ln 103.99 66.46 105.8 69.58 g_dk3s_lay_thin)
  (dk3s_iso_ln 106.35 70.54 107.64 72.77 g_dk3s_lay_thin)
  (dk3s_iso_ln 105.46 67.31 109.11 73.62 g_dk3s_lay_thin)
  (dk3s_iso_ln 106.93 68.15 110.58 74.47 g_dk3s_lay_thin)
  (dk3s_iso_ln 108.4 69 112.05 75.32 g_dk3s_lay_thin)
  (dk3s_iso_ln 109.87 69.85 113.51 76.16 g_dk3s_lay_thin)
  (dk3s_iso_ln 111.34 70.7 114.98 77.01 g_dk3s_lay_thin)
  (dk3s_iso_ln 112.81 71.55 116.45 77.86 g_dk3s_lay_thin)
  (dk3s_iso_ln 114.28 72.4 117.92 78.71 g_dk3s_lay_thin)
  (dk3s_iso_ln 115.75 73.24 118.97 78.83 g_dk3s_lay_thin)
  (dk3s_iso_ln 117.22 74.09 119.02 77.22 g_dk3s_lay_thin)
  (dk3s_iso_ln 118.69 74.94 120.49 78.07 g_dk3s_lay_thin)
  (dk3s_iso_ln 120.16 75.79 121.96 78.92 g_dk3s_lay_thin)
  (dk3s_iso_ln 121.63 76.64 123.43 79.76 g_dk3s_lay_thin)
  (dk3s_iso_ln 123.1 77.49 124.9 80.61 g_dk3s_lay_thin)
  (dk3s_iso_ln 124.57 78.34 126.37 81.46 g_dk3s_lay_thin)
  (dk3s_iso_ln 126.04 79.18 127.84 82.31 g_dk3s_lay_thin)
  (dk3s_iso_ln 127.51 80.03 129.31 83.16 g_dk3s_lay_thin)
  (dk3s_iso_ln 128.98 80.88 130.78 84.01 g_dk3s_lay_thin)
  (dk3s_iso_ln 130.45 81.73 132.25 84.86 g_dk3s_lay_thin)
  (dk3s_iso_ln 131.92 82.58 133.72 85.7 g_dk3s_lay_thin)
  (dk3s_iso_ln 133.38 83.43 135.19 86.55 g_dk3s_lay_thin)
  (dk3s_iso_ln 134.85 84.28 136.66 87.4 g_dk3s_lay_thin)
  (dk3s_iso_ln 136.32 85.12 138.19 88.36 g_dk3s_lay_thin)
  (dk3s_iso_ln 137.79 85.97 139.66 89.21 g_dk3s_lay_thin)
  (dk3s_iso_ln 139.26 86.82 141.13 90.06 g_dk3s_lay_thin)
  (dk3s_iso_ln 140.73 87.67 141.7 89.35 g_dk3s_lay_thin)
  (dk3s_iso_ln 100.57 65.74 101.66 65.11 g_dk3s_lay_thin)
  (dk3s_iso_ln 101.33 67 103.13 65.96 g_dk3s_lay_thin)
  (dk3s_iso_ln 102.8 67.85 104.6 66.81 g_dk3s_lay_thin)
  (dk3s_iso_ln 104.27 68.7 106.07 67.66 g_dk3s_lay_thin)
  (dk3s_iso_ln 105.74 69.55 107.54 68.51 g_dk3s_lay_thin)
  (dk3s_iso_ln 106.46 70.83 109.01 69.36 g_dk3s_lay_thin)
  (dk3s_iso_ln 107 72.21 110.48 70.2 g_dk3s_lay_thin)
  (dk3s_iso_ln 108.31 73.16 111.95 71.05 g_dk3s_lay_thin)
  (dk3s_iso_ln 109.78 74.01 113.42 71.9 g_dk3s_lay_thin)
  (dk3s_iso_ln 111.25 74.85 114.89 72.75 g_dk3s_lay_thin)
  (dk3s_iso_ln 112.71 75.7 116.36 73.6 g_dk3s_lay_thin)
  (dk3s_iso_ln 114.18 76.55 117.83 74.45 g_dk3s_lay_thin)
  (dk3s_iso_ln 115.65 77.4 119.3 75.29 g_dk3s_lay_thin)
  (dk3s_iso_ln 117.12 78.25 120.77 76.14 g_dk3s_lay_thin)
  (dk3s_iso_ln 118.59 79.1 118.97 78.88 g_dk3s_lay_thin)
  (dk3s_iso_ln 120.43 78.03 122.24 76.99 g_dk3s_lay_thin)
  (dk3s_iso_ln 121.9 78.88 123.71 77.84 g_dk3s_lay_thin)
  (dk3s_iso_ln 123.37 79.73 125.18 78.69 g_dk3s_lay_thin)
  (dk3s_iso_ln 124.84 80.58 126.65 79.54 g_dk3s_lay_thin)
  (dk3s_iso_ln 126.31 81.43 128.12 80.39 g_dk3s_lay_thin)
  (dk3s_iso_ln 127.78 82.28 129.59 81.23 g_dk3s_lay_thin)
  (dk3s_iso_ln 129.25 83.13 131.06 82.08 g_dk3s_lay_thin)
  (dk3s_iso_ln 130.72 83.97 132.53 82.93 g_dk3s_lay_thin)
  (dk3s_iso_ln 132.19 84.82 134 83.78 g_dk3s_lay_thin)
  (dk3s_iso_ln 133.66 85.67 135.47 84.63 g_dk3s_lay_thin)
  (dk3s_iso_ln 135.13 86.52 136.94 85.48 g_dk3s_lay_thin)
  (dk3s_iso_ln 136.6 87.37 138.41 86.33 g_dk3s_lay_thin)
  (dk3s_iso_ln 138.01 88.25 139.88 87.17 g_dk3s_lay_thin)
  (dk3s_iso_ln 139.48 89.1 141.34 88.02 g_dk3s_lay_thin)
  (dk3s_iso_ln 140.94 89.95 141.27 89.76 g_dk3s_lay_thin)
  (dk3s_iso_ln 141.38 89.7 141.7 89.51 g_dk3s_lay_thin)
  (dk3s_iso_ln 100.57 62.22 101.38 63.63 g_dk3s_lay_thin)
  (dk3s_iso_ln 101.36 61.89 102.85 64.48 g_dk3s_lay_thin)
  (dk3s_iso_ln 102.83 62.74 104.32 65.33 g_dk3s_lay_thin)
  (dk3s_iso_ln 104.3 63.59 105.79 66.18 g_dk3s_lay_thin)
  (dk3s_iso_ln 105.77 64.44 107.26 67.02 g_dk3s_lay_thin)
  (dk3s_iso_ln 107.24 65.29 108.73 67.87 g_dk3s_lay_thin)
  (dk3s_iso_ln 108.71 66.14 110.2 68.72 g_dk3s_lay_thin)
  (dk3s_iso_ln 110.18 66.99 111.67 69.57 g_dk3s_lay_thin)
  (dk3s_iso_ln 111.65 67.83 113.14 70.42 g_dk3s_lay_thin)
  (dk3s_iso_ln 113.11 68.68 114.61 71.27 g_dk3s_lay_thin)
  (dk3s_iso_ln 114.58 69.53 116.08 72.11 g_dk3s_lay_thin)
  (dk3s_iso_ln 116.05 70.38 117.55 72.96 g_dk3s_lay_thin)
  (dk3s_iso_ln 117.52 71.23 119.02 73.81 g_dk3s_lay_thin)
  (dk3s_iso_ln 118.99 72.08 120.48 74.66 g_dk3s_lay_thin)
  (dk3s_iso_ln 120.46 72.93 121.95 75.51 g_dk3s_lay_thin)
  (dk3s_iso_ln 121.93 73.77 123.42 76.36 g_dk3s_lay_thin)
  (dk3s_iso_ln 123.4 74.62 124.89 77.21 g_dk3s_lay_thin)
  (dk3s_iso_ln 124.87 75.47 126.36 78.05 g_dk3s_lay_thin)
  (dk3s_iso_ln 126.34 76.32 127.83 78.9 g_dk3s_lay_thin)
  (dk3s_iso_ln 127.81 77.17 129.3 79.75 g_dk3s_lay_thin)
  (dk3s_iso_ln 129.28 78.02 130.77 80.6 g_dk3s_lay_thin)
  (dk3s_iso_ln 130.75 78.87 132.24 81.45 g_dk3s_lay_thin)
  (dk3s_iso_ln 132.22 79.71 133.71 82.3 g_dk3s_lay_thin)
  (dk3s_iso_ln 133.69 80.56 135.18 83.15 g_dk3s_lay_thin)
  (dk3s_iso_ln 135.16 81.41 136.65 83.99 g_dk3s_lay_thin)
  (dk3s_iso_ln 136.63 82.26 138.12 84.84 g_dk3s_lay_thin)
  (dk3s_iso_ln 138.1 83.11 139.59 85.69 g_dk3s_lay_thin)
  (dk3s_iso_ln 139.57 83.96 141.06 86.54 g_dk3s_lay_thin)
  (dk3s_iso_ln 141.04 84.81 141.7 85.96 g_dk3s_lay_thin)
  (dk3s_iso_ln 100.57 62.35 101.36 61.89 g_dk3s_lay_thin)
  (dk3s_iso_ln 101.34 63.6 102.83 62.74 g_dk3s_lay_thin)
  (dk3s_iso_ln 102.81 64.45 104.3 63.59 g_dk3s_lay_thin)
  (dk3s_iso_ln 104.28 65.3 105.77 64.44 g_dk3s_lay_thin)
  (dk3s_iso_ln 105.74 66.15 107.24 65.29 g_dk3s_lay_thin)
  (dk3s_iso_ln 107.21 67 108.71 66.14 g_dk3s_lay_thin)
  (dk3s_iso_ln 108.68 67.85 110.18 66.99 g_dk3s_lay_thin)
  (dk3s_iso_ln 110.15 68.7 111.65 67.83 g_dk3s_lay_thin)
  (dk3s_iso_ln 111.62 69.54 113.11 68.68 g_dk3s_lay_thin)
  (dk3s_iso_ln 113.09 70.39 114.58 69.53 g_dk3s_lay_thin)
  (dk3s_iso_ln 114.56 71.24 116.05 70.38 g_dk3s_lay_thin)
  (dk3s_iso_ln 116.03 72.09 117.52 71.23 g_dk3s_lay_thin)
  (dk3s_iso_ln 117.5 72.94 118.99 72.08 g_dk3s_lay_thin)
  (dk3s_iso_ln 118.97 73.79 120.46 72.93 g_dk3s_lay_thin)
  (dk3s_iso_ln 120.44 74.64 121.93 73.77 g_dk3s_lay_thin)
  (dk3s_iso_ln 121.91 75.48 123.4 74.62 g_dk3s_lay_thin)
  (dk3s_iso_ln 123.38 76.33 124.87 75.47 g_dk3s_lay_thin)
  (dk3s_iso_ln 124.85 77.18 126.34 76.32 g_dk3s_lay_thin)
  (dk3s_iso_ln 126.32 78.03 127.81 77.17 g_dk3s_lay_thin)
  (dk3s_iso_ln 127.79 78.88 129.28 78.02 g_dk3s_lay_thin)
  (dk3s_iso_ln 129.26 79.73 130.75 78.87 g_dk3s_lay_thin)
  (dk3s_iso_ln 130.73 80.58 132.22 79.71 g_dk3s_lay_thin)
  (dk3s_iso_ln 132.2 81.42 133.69 80.56 g_dk3s_lay_thin)
  (dk3s_iso_ln 133.67 82.27 135.16 81.41 g_dk3s_lay_thin)
  (dk3s_iso_ln 135.14 83.12 136.63 82.26 g_dk3s_lay_thin)
  (dk3s_iso_ln 136.61 83.97 138.1 83.11 g_dk3s_lay_thin)
  (dk3s_iso_ln 138.08 84.82 139.57 83.96 g_dk3s_lay_thin)
  (dk3s_iso_ln 139.55 85.67 141.04 84.81 g_dk3s_lay_thin)
  (dk3s_iso_ln 141.02 86.51 141.7 86.12 g_dk3s_lay_thin)
  (dk3s_iso_ln 101.25 61.05 102.01 61.05 g_dk3s_lay_thin)
  (dk3s_iso_ln 101.36 61.89 103.48 61.89 g_dk3s_lay_thin)
  (dk3s_iso_ln 102.83 62.74 104.95 62.74 g_dk3s_lay_thin)
  (dk3s_iso_ln 104.3 63.59 106.42 63.59 g_dk3s_lay_thin)
  (dk3s_iso_ln 105.77 64.44 107.89 64.44 g_dk3s_lay_thin)
  (dk3s_iso_ln 107.24 65.29 109.36 65.29 g_dk3s_lay_thin)
  (dk3s_iso_ln 108.71 66.14 110.83 66.14 g_dk3s_lay_thin)
  (dk3s_iso_ln 110.18 66.99 112.3 66.99 g_dk3s_lay_thin)
  (dk3s_iso_ln 111.65 67.83 113.77 67.83 g_dk3s_lay_thin)
  (dk3s_iso_ln 113.11 68.68 115.24 68.68 g_dk3s_lay_thin)
  (dk3s_iso_ln 114.58 69.53 116.71 69.53 g_dk3s_lay_thin)
  (dk3s_iso_ln 116.05 70.38 118.18 70.38 g_dk3s_lay_thin)
  (dk3s_iso_ln 117.52 71.23 119.65 71.23 g_dk3s_lay_thin)
  (dk3s_iso_ln 118.99 72.08 121.12 72.08 g_dk3s_lay_thin)
  (dk3s_iso_ln 120.46 72.93 122.59 72.93 g_dk3s_lay_thin)
  (dk3s_iso_ln 121.93 73.77 124.05 73.77 g_dk3s_lay_thin)
  (dk3s_iso_ln 123.4 74.62 125.52 74.62 g_dk3s_lay_thin)
  (dk3s_iso_ln 124.87 75.47 126.99 75.47 g_dk3s_lay_thin)
  (dk3s_iso_ln 126.34 76.32 128.46 76.32 g_dk3s_lay_thin)
  (dk3s_iso_ln 127.81 77.17 129.93 77.17 g_dk3s_lay_thin)
  (dk3s_iso_ln 129.28 78.02 131.4 78.02 g_dk3s_lay_thin)
  (dk3s_iso_ln 130.75 78.87 132.87 78.87 g_dk3s_lay_thin)
  (dk3s_iso_ln 132.22 79.71 134.34 79.71 g_dk3s_lay_thin)
  (dk3s_iso_ln 133.69 80.56 135.81 80.56 g_dk3s_lay_thin)
  (dk3s_iso_ln 135.16 81.41 137.28 81.41 g_dk3s_lay_thin)
  (dk3s_iso_ln 136.63 82.26 138.75 82.26 g_dk3s_lay_thin)
  (dk3s_iso_ln 138.1 83.11 140.22 83.11 g_dk3s_lay_thin)
  (dk3s_iso_ln 139.57 83.96 141.69 83.96 g_dk3s_lay_thin)
  (dk3s_iso_ln 141.04 84.81 142.37 84.81 g_dk3s_lay_thin)
  (dk3s_iso_ln 101.36 60.98 101.36 61.89 g_dk3s_lay_thin)
  (dk3s_iso_ln 102.83 61.52 102.83 62.74 g_dk3s_lay_thin)
  (dk3s_iso_ln 104.3 62.37 104.3 63.59 g_dk3s_lay_thin)
  (dk3s_iso_ln 105.77 63.22 105.77 64.44 g_dk3s_lay_thin)
  (dk3s_iso_ln 107.24 64.06 107.24 65.29 g_dk3s_lay_thin)
  (dk3s_iso_ln 108.71 64.91 108.71 66.14 g_dk3s_lay_thin)
  (dk3s_iso_ln 110.18 65.76 110.18 66.99 g_dk3s_lay_thin)
  (dk3s_iso_ln 111.65 66.61 111.65 67.83 g_dk3s_lay_thin)
  (dk3s_iso_ln 113.11 67.46 113.11 68.68 g_dk3s_lay_thin)
  (dk3s_iso_ln 114.58 68.31 114.58 69.53 g_dk3s_lay_thin)
  (dk3s_iso_ln 116.05 69.16 116.05 70.38 g_dk3s_lay_thin)
  (dk3s_iso_ln 117.52 70 117.52 71.23 g_dk3s_lay_thin)
  (dk3s_iso_ln 118.99 70.85 118.99 72.08 g_dk3s_lay_thin)
  (dk3s_iso_ln 120.46 71.7 120.46 72.93 g_dk3s_lay_thin)
  (dk3s_iso_ln 121.93 72.55 121.93 73.77 g_dk3s_lay_thin)
  (dk3s_iso_ln 123.4 73.4 123.4 74.62 g_dk3s_lay_thin)
  (dk3s_iso_ln 124.87 74.25 124.87 75.47 g_dk3s_lay_thin)
  (dk3s_iso_ln 126.34 75.09 126.34 76.32 g_dk3s_lay_thin)
  (dk3s_iso_ln 127.81 75.94 127.81 77.17 g_dk3s_lay_thin)
  (dk3s_iso_ln 129.28 76.79 129.28 78.02 g_dk3s_lay_thin)
  (dk3s_iso_ln 130.75 77.64 130.75 78.87 g_dk3s_lay_thin)
  (dk3s_iso_ln 132.22 78.49 132.22 79.71 g_dk3s_lay_thin)
  (dk3s_iso_ln 133.69 79.34 133.69 80.56 g_dk3s_lay_thin)
  (dk3s_iso_ln 135.16 80.19 135.16 81.41 g_dk3s_lay_thin)
  (dk3s_iso_ln 136.63 81.03 136.63 82.26 g_dk3s_lay_thin)
  (dk3s_iso_ln 138.1 81.88 138.1 83.11 g_dk3s_lay_thin)
  (dk3s_iso_ln 139.57 82.73 139.57 83.96 g_dk3s_lay_thin)
  (dk3s_iso_ln 141.04 83.58 141.04 84.81 g_dk3s_lay_thin)
  (dk3s_iso_ln 142.51 84.43 142.51 84.72 g_dk3s_lay_thin)
  (dk3s_iso_ln 104.35 59.35 105.83 59.35 g_dk3s_lay_thin)
  (dk3s_iso_ln 105.82 60.2 107.29 60.2 g_dk3s_lay_thin)
  (dk3s_iso_ln 107.29 61.05 108.76 61.05 g_dk3s_lay_thin)
  (dk3s_iso_ln 108.76 61.89 110.23 61.89 g_dk3s_lay_thin)
  (dk3s_iso_ln 111.34 61.89 113.91 61.89 g_dk3s_lay_thin)
  (dk3s_iso_ln 110.23 62.74 115.38 62.74 g_dk3s_lay_thin)
  (dk3s_iso_ln 111.7 63.59 116.85 63.59 g_dk3s_lay_thin)
  (dk3s_iso_ln 113.17 64.44 118.32 64.44 g_dk3s_lay_thin)
  (dk3s_iso_ln 114.64 65.29 119.79 65.29 g_dk3s_lay_thin)
  (dk3s_iso_ln 116.11 66.14 121.26 66.14 g_dk3s_lay_thin)
  (dk3s_iso_ln 117.58 66.99 122.73 66.99 g_dk3s_lay_thin)
  (dk3s_iso_ln 119.05 67.83 124.2 67.83 g_dk3s_lay_thin)
  (dk3s_iso_ln 120.52 68.68 124.83 68.68 g_dk3s_lay_thin)
  (dk3s_iso_ln 121.99 69.53 123.46 69.53 g_dk3s_lay_thin)
  (dk3s_iso_ln 123.46 70.38 124.93 70.38 g_dk3s_lay_thin)
  (dk3s_iso_ln 124.93 71.23 126.4 71.23 g_dk3s_lay_thin)
  (dk3s_iso_ln 126.4 72.08 127.87 72.08 g_dk3s_lay_thin)
  (dk3s_iso_ln 127.87 72.93 129.34 72.93 g_dk3s_lay_thin)
  (dk3s_iso_ln 129.34 73.77 130.81 73.77 g_dk3s_lay_thin)
  (dk3s_iso_ln 130.81 74.62 132.28 74.62 g_dk3s_lay_thin)
  (dk3s_iso_ln 132.28 75.47 133.75 75.47 g_dk3s_lay_thin)
  (dk3s_iso_ln 133.75 76.32 135.22 76.32 g_dk3s_lay_thin)
  (dk3s_iso_ln 135.22 77.17 136.69 77.17 g_dk3s_lay_thin)
  (dk3s_iso_ln 136.69 78.02 138.16 78.02 g_dk3s_lay_thin)
  (dk3s_iso_ln 138.16 78.87 139.63 78.87 g_dk3s_lay_thin)
  (dk3s_iso_ln 139.63 79.71 141.1 79.71 g_dk3s_lay_thin)
  (dk3s_iso_ln 141.1 80.56 142.7 80.56 g_dk3s_lay_thin)
  (dk3s_iso_ln 142.56 81.41 144.17 81.41 g_dk3s_lay_thin)
  (dk3s_iso_ln 144.03 82.26 145.64 82.26 g_dk3s_lay_thin)
  (dk3s_iso_ln 104.3 59.29 104.3 59.32 g_dk3s_lay_thin)
  (dk3s_iso_ln 105.77 59.32 105.77 60.17 g_dk3s_lay_thin)
  (dk3s_iso_ln 107.24 60.16 107.24 61.01 g_dk3s_lay_thin)
  (dk3s_iso_ln 108.71 61.01 108.71 61.86 g_dk3s_lay_thin)
  (dk3s_iso_ln 110.18 61.86 110.18 62.71 g_dk3s_lay_thin)
  (dk3s_iso_ln 111.65 61.85 111.65 63.56 g_dk3s_lay_thin)
  (dk3s_iso_ln 113.11 61.62 113.11 64.41 g_dk3s_lay_thin)
  (dk3s_iso_ln 114.58 62.28 114.58 65.26 g_dk3s_lay_thin)
  (dk3s_iso_ln 116.05 63.13 116.05 66.11 g_dk3s_lay_thin)
  (dk3s_iso_ln 117.52 63.98 117.52 66.95 g_dk3s_lay_thin)
  (dk3s_iso_ln 118.99 64.83 118.99 67.8 g_dk3s_lay_thin)
  (dk3s_iso_ln 120.46 65.68 120.46 68.65 g_dk3s_lay_thin)
  (dk3s_iso_ln 121.93 66.52 121.93 69.5 g_dk3s_lay_thin)
  (dk3s_iso_ln 123.4 67.37 123.4 70.35 g_dk3s_lay_thin)
  (dk3s_iso_ln 124.87 68.22 124.87 68.66 g_dk3s_lay_thin)
  (dk3s_iso_ln 124.87 70.35 124.87 71.2 g_dk3s_lay_thin)
  (dk3s_iso_ln 126.34 71.19 126.34 72.04 g_dk3s_lay_thin)
  (dk3s_iso_ln 127.81 72.04 127.81 72.89 g_dk3s_lay_thin)
  (dk3s_iso_ln 129.28 72.89 129.28 73.74 g_dk3s_lay_thin)
  (dk3s_iso_ln 130.75 73.74 130.75 74.59 g_dk3s_lay_thin)
  (dk3s_iso_ln 132.22 74.59 132.22 75.44 g_dk3s_lay_thin)
  (dk3s_iso_ln 133.69 75.44 133.69 76.29 g_dk3s_lay_thin)
  (dk3s_iso_ln 135.16 76.29 135.16 77.14 g_dk3s_lay_thin)
  (dk3s_iso_ln 136.63 77.13 136.63 77.98 g_dk3s_lay_thin)
  (dk3s_iso_ln 138.1 77.98 138.1 78.83 g_dk3s_lay_thin)
  (dk3s_iso_ln 139.57 78.83 139.57 79.68 g_dk3s_lay_thin)
  (dk3s_iso_ln 141.04 79.68 141.04 80.53 g_dk3s_lay_thin)
  (dk3s_iso_ln 142.51 80.45 142.51 81.38 g_dk3s_lay_thin)
  (dk3s_iso_ln 143.98 81.3 143.98 82.23 g_dk3s_lay_thin)
  (dk3s_iso_ln 145.45 82.15 145.45 82.53 g_dk3s_lay_thin)
  (dk3s_iso_ln 145.45 82.65 145.45 83.03 g_dk3s_lay_thin)
  (dk3s_iso_ln 3.31 5.29 147.59 88.59 g_dk3s_lay_axis)
  (dk3s_leader (dk3s_iso_p 14.35 11.91) (dk3s_iso_p 37 1) 1 "Наконечник")
  (dk3s_leader (dk3s_iso_p 28.86 30.14) (dk3s_iso_p 47 58) -1 "Труба защитная")
  (dk3s_leader (dk3s_iso_p 56.73 39.89) (dk3s_iso_p 56 70) -1 "Мостик (2 шт.)")
  (dk3s_leader (dk3s_iso_p 73.53 42.32) (dk3s_iso_p 74 82) -1 "Трубка токоотвода РЭ")
  (dk3s_leader (dk3s_iso_p 113.3 75.04) (dk3s_iso_p 107 108) -1 "Сальник")
  (dk3s_leader (dk3s_iso_p 120.66 79.29) (dk3s_iso_p 118 120) -1 "Грундбукса")
  (dk3s_leader (dk3s_iso_p 123.73 81.21) (dk3s_iso_p 128 132) -1 "Шайба пружинная (гровер)")
  (dk3s_leader (dk3s_iso_p 132.78 91.54) (dk3s_iso_p 140 144) -1 "Гайка нажимная")
  (dk3s_leader (dk3s_iso_p 127.59 56.04) (dk3s_iso_p 145 40) 1 "Узел сальника")
  (dk3s_dim_obl (dk3s_iso_p 129.2549 70.6266) (dk3s_iso_p 131.2034 71.7516) (dk3s_iso_p 142.7865 62.8141) 30.00 -60.00 "" (dk3s_iso_p 149.9312 66.9391))   ; толщина гровера
)
;;; картинка 271.1 x 172.5 мм бумаги; полилиний 553, точек 2292, штриховка 528, выносок 9, размеров 1
;;; === ISO END ===

(princ "\nDK3S v1.3.5 loaded. Command: DK3S")
(princ)
